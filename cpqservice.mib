-- ****************************************************************************
-- ****************************************************************************
--
--                  Service Incident Information
--         Management Information Base for SNMP Network Management
--
--
--      Copyright 1998,2003 Hewlett-Packard Development Company, L.P.
--
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
--      The Services Incident MIB provides Service Incident notification information.
--
-- ****************************************************************************


CPQSERVICE-MIB DEFINITIONS ::= BEGIN

    IMPORTS
       DisplayString           FROM RFC1213-MIB
       IpAddress	       FROM RFC1155-SMI
       OBJECT-TYPE             FROM RFC-1212
       TRAP-TYPE               FROM RFC-1215
       compaq                  FROM CPQHOST-MIB
       sysName                 FROM RFC1213-MIB;

--    compaq                  OBJECT IDENTIFIER ::= { enterprises 232 }
    cpqService              OBJECT IDENTIFIER ::= { compaq 164 }
    cpqServiceMibRev        OBJECT IDENTIFIER ::= { cpqService 1 }
    cpqServiceIncident      OBJECT IDENTIFIER ::= { cpqService 2 }
    cpqService3Incident     OBJECT IDENTIFIER ::= { cpqService 3 }


-- ****************************************************************************
--   Service Information MIB Revision
--   ================================
--
-- The compaq enterprise               (1.3.6.1.4.1.232)
--      cpqService Group               (1.3.6.1.4.1.232.164)
--      cpqServiceMibRev Group         (1.3.6.1.4.1.232.164.1)
--
--      Implementation of the cpqServiceMibRev group is mandatory for all agents
--      supporting the SI MIB.
--
--      An SNMP Agent conforming to this document will return a
--      cpqServiceMibRevMajor of one (2) and a cpqServiceMibRevMinor of zero (0).
--
--
-- ****************************************************************************82

    cpqServiceMibRevMajor OBJECT-TYPE
        SYNTAX  INTEGER (1..65535)
        ACCESS  read-only
        STATUS  mandatory
        DESCRIPTION
            "The Major Revision level of the MIB.

            A change in the major revision level represents a major change
            in the architecture of the MIB.  A change in the major revision
            level may indicate a significant change in the information
            supported and/or the meaning of the supported information.
            Correct interpretation of data may require a MIB document with
            the same major revision level."
        ::= { cpqServiceMibRev 2 }

    cpqServiceMibRevMinor OBJECT-TYPE
        SYNTAX  INTEGER (0..65535)
        ACCESS  read-only
        STATUS  mandatory
        DESCRIPTION
            "The Minor Revision level of the MIB.

            A change in the minor revision level may represent some minor
            additional support, no changes to any pre-existing information
            has occurred."
        ::= { cpqServiceMibRev 1 }


-- ****************************************************************************
--   Service Incident Common
--   =======================
--
-- The compaq enterprise               (1.3.6.1.4.1.232)
--      cpqService Group                    (1.3.6.1.4.1.232.164)
--       cpqService Incident Group          (1.3.6.1.4.1.232.164.2)
--
--      The cpqServiceIncident group contains the general information about the
--      service event.
--
--  Implementation of the cpqServiceIncident group is mandatory for all
--  agents that support the SI MIB.
--
-- ****************************************************************************

   cpqServiceIncidentSeverity OBJECT-TYPE
        SYNTAX  INTEGER {
            important(1),
            informational(2)
            }
        ACCESS  read-only
        STATUS  deprecated
        DESCRIPTION
            "The severity of the service incident."
        ::= { cpqServiceIncident 1 }

   cpqServiceIncidentStatus OBJECT-TYPE

        SYNTAX  INTEGER {
            other(1),
            intransit(2),
            delivered(3),
           undelivered(4),
            assigned(5),
            closed(6),
	   submitted_to_ISEE(7)
            }
        ACCESS  read-only
        STATUS  mandatory
        DESCRIPTION
           "The status of the service incident."

        ::= { cpqServiceIncident 2 }

    cpqServiceIncidentInformation OBJECT-TYPE
        SYNTAX  DisplayString (SIZE (0..255))
        ACCESS  read-only
        STATUS  mandatory
        DESCRIPTION
            "Provides the URL to the event analysis report. "
--     CpqServiceIncidentInformation is a URL pointing to
--     the Service Rule describing the serviceable event.
        ::= { cpqServiceIncident 3 }

    cpqServiceIncidentEvent OBJECT-TYPE
        SYNTAX  DisplayString (SIZE (0..255))
        ACCESS  read-only
        STATUS  mandatory
        DESCRIPTION
            "Brief description of the event that initiated the service incident."
        ::= { cpqServiceIncident 4 }

    cpqServiceIncidentUniqueID OBJECT-TYPE
        SYNTAX  DisplayString (SIZE (0..255))
        ACCESS  read-only
        STATUS  mandatory
        DESCRIPTION
            "Unique Event Analysis Identifier assigned to the incident."
        ::= { cpqServiceIncident 5 }

    cpqServiceIncidentTimeofOriginalEvent OBJECT-TYPE
        SYNTAX  DisplayString (SIZE (0..255))
	ACCESS read-only
	STATUS mandatory
	DESCRIPTION
	    "Time of the original event this service event relates to."
--      Time format in the form of "12 September 2003 23:23:23.000".
	::= { cpqServiceIncident 6 }

    cpqServiceIncidentSourceSystemName OBJECT-TYPE
	SYNTAX DisplayString (SIZE (0..255))
	ACCESS read-only
	STATUS mandatory
	DESCRIPTION
	    "Name of the system this service event relates to."
	::= { cpqServiceIncident 7 }

    cpqServiceIncidentIPAddessOfSource OBJECT-TYPE
	SYNTAX IpAddress
	ACCESS read-only
	STATUS mandatory
	DESCRIPTION
	    "IP Address of the system this service event relates to."
	::= { cpqServiceIncident 8 }

   cpqServiceISEEIncidentInformation OBJECT-TYPE
        SYNTAX  DisplayString (SIZE (0..255))
        ACCESS  read-only
        STATUS  mandatory
        DESCRIPTION
            "This is a URL pointing to the Service Incident status in ISEE if available."
--     This is a URL pointing to the Service Incident status if ISEE is capable of
--     providing this information. This would be an XML tag including a text field
--     identifying the status of the incident and an attached URL pointing to
--     incident information accessed via the ISEE client or the SPOP. If the ISEE
--     client can not provide this tag information, but could provide status
--     information, then the returned values would be as defined here.
        ::= { cpqServiceIncident 9 }

    cpqServiceIncidentIdentifier OBJECT-TYPE
        SYNTAX  DisplayString (SIZE (0..255))
        ACCESS  read-only
        STATUS  mandatory
        DESCRIPTION
            "Service Incident Identifier assigned to the incident report by the
             ISEE client."
        ::= { cpqServiceIncident 10 }

    cpqServiceIncidentReceiveTrapOID OBJECT-TYPE
        SYNTAX OBJECT IDENTIFIER
	ACCESS read-only
	STATUS mandatory
	DESCRIPTION
	    "The ID of the originally received event."
	::= { cpqServiceIncident 11 }

    cpqServiceIncidentFilterOID OBJECT-TYPE
        SYNTAX OBJECT IDENTIFIER
	ACCESS read-only
	STATUS deprecated
	DESCRIPTION
	    "The OID of the value that is used by the OSEM filter."
	::= { cpqServiceIncident 12 }

    cpqServiceIncidentFilterValue OBJECT-TYPE
	SYNTAX DisplayString (SIZE (0..255))
	ACCESS read-only
	STATUS deprecated
	DESCRIPTION
	    "The value contained in the Filter OID."
	::= { cpqServiceIncident 13 }

    cpqServiceRecommendedAction1 OBJECT-TYPE
        SYNTAX  DisplayString (SIZE (0..255))
        ACCESS  read-only
        STATUS  mandatory
        DESCRIPTION
            "Recommended action."
        ::= { cpqServiceIncident 14 }

    cpqServiceRecommendedAction2 OBJECT-TYPE
        SYNTAX  DisplayString (SIZE (0..255))
        ACCESS  read-only
        STATUS  mandatory
        DESCRIPTION
            "Recommended action continued"
        ::= { cpqServiceIncident 15 }

    cpqServiceRecommendedAction3 OBJECT-TYPE
        SYNTAX  DisplayString (SIZE (0..255))
        ACCESS  read-only
        STATUS  mandatory
        DESCRIPTION
            "Recommended action continued"
        ::= { cpqServiceIncident 16 }

    cpqServiceCustomerSelfRepairInstructionURL OBJECT-TYPE
        SYNTAX  DisplayString (SIZE (0..255))
        ACCESS  read-only
        STATUS  mandatory
        DESCRIPTION
            "A URL pointing to additional repair information"
        ::= { cpqServiceIncident 17 }

    cpqServiceEventSeverity OBJECT-TYPE
        SYNTAX  INTEGER {
	    critical(1),
	    major(2),
	    minor(3),
	    warning(4),
	    informational(5)
            }
        ACCESS  read-only
        STATUS  mandatory
        DESCRIPTION
            "The severity of the service incident."
        ::= { cpqServiceIncident 18 }

    cpqServiceAnalyzerSystemName OBJECT-TYPE
	SYNTAX DisplayString (SIZE (0..255))
	ACCESS read-only
	STATUS mandatory
	DESCRIPTION
	    "Name of the system this service event was analyzed on."
	::= { cpqServiceIncident 19 }

    cpqServiceFRUList1 OBJECT-TYPE
        SYNTAX  DisplayString (SIZE (0..255))
        ACCESS  read-only
        STATUS  mandatory
        DESCRIPTION
            "Replaceable Unit information"
        ::= { cpqServiceIncident 20 }

    cpqServiceFRUList2 OBJECT-TYPE
        SYNTAX  DisplayString (SIZE (0..255))
        ACCESS  read-only
        STATUS  mandatory
        DESCRIPTION
            "Replaceable Unit information continued"
        ::= { cpqServiceIncident 21 }

    cpqServiceFRUList3 OBJECT-TYPE
        SYNTAX  DisplayString (SIZE (0..255))
        ACCESS  read-only
        STATUS  mandatory
        DESCRIPTION
            "Replaceable Unit information continued"
        ::= { cpqServiceIncident 22 }

    cpqServiceFRUList4 OBJECT-TYPE
        SYNTAX  DisplayString (SIZE (0..255))
        ACCESS  read-only
        STATUS  mandatory
        DESCRIPTION
            "Replaceable Unit information continued"
        ::= { cpqServiceIncident 23 }

    cpqServiceLocation1 OBJECT-TYPE
        SYNTAX  DisplayString (SIZE (0..255))
        ACCESS  read-only
        STATUS  mandatory
        DESCRIPTION
            "Replaceable Unit location"
        ::= { cpqServiceIncident 24 }

    cpqServiceLocation2 OBJECT-TYPE
        SYNTAX  DisplayString (SIZE (0..255))
        ACCESS  read-only
        STATUS  mandatory
        DESCRIPTION
            "Replaceable Unit location continued"
        ::= { cpqServiceIncident 25 }

-- ****************************************************************************
--   Service Incident Common legacy definition
--   =========================================
--
-- The compaq enterprise               (1.3.6.1.4.1.232)
--      cpqService Group                    (1.3.6.1.4.1.232.164)
--       cpqService3 Incident Group          (1.3.6.1.4.1.232.164.3)
--
--      The cpqService3Incident group contains the general information about the
--      service event.
--
--
-- ****************************************************************************

   cpqService3IncidentSeverity OBJECT-TYPE
        SYNTAX  INTEGER {
            important(1),
            informational(2)
            }
        ACCESS  read-only
        STATUS  deprecated
        DESCRIPTION
            "The severity of the service incident."
        ::= { cpqService3Incident 1 }

   cpqService3IncidentStatus OBJECT-TYPE

        SYNTAX  INTEGER {
            other(1),
            intransit(2),
            delivered(3),
           undelivered(4),
            assigned(5),
            closed(6),
	   submitted_to_ISEE(7)
            }
        ACCESS  read-only
        STATUS  mandatory
        DESCRIPTION
           "The status of the service incident."

        ::= { cpqService3Incident 2 }

    cpqService3IncidentInformation OBJECT-TYPE
        SYNTAX  DisplayString (SIZE (0..255))
        ACCESS  read-only
        STATUS  mandatory
        DESCRIPTION
            "Provides the URL to the event analysis report. "
--     CpqServiceIncidentInformation is a URL pointing to
--     the Service Rule describing the serviceable event.
        ::= { cpqService3Incident 3 }

    cpqService3IncidentEvent OBJECT-TYPE
        SYNTAX  DisplayString (SIZE (0..255))
        ACCESS  read-only
        STATUS  mandatory
        DESCRIPTION
            "Brief description of the event that initiated the service incident."
        ::= { cpqService3Incident 4 }

    cpqService3IncidentUniqueID OBJECT-TYPE
        SYNTAX  DisplayString (SIZE (0..255))
        ACCESS  read-only
        STATUS  mandatory
        DESCRIPTION
            "Unique Event Analysis Identifier assigned to the incident."
        ::= { cpqService3Incident 5 }

    cpqService3IncidentTimeofOriginalEvent OBJECT-TYPE
        SYNTAX  DisplayString (SIZE (0..255))
	ACCESS read-only
	STATUS mandatory
	DESCRIPTION
	    "Time of the original event this service event relates to."
--      Time format in the form of "12 September 2003 23:23:23.000".
	::= { cpqService3Incident 6 }

    cpqService3IncidentSourceSystemName OBJECT-TYPE
	SYNTAX DisplayString (SIZE (0..255))
	ACCESS read-only
	STATUS mandatory
	DESCRIPTION
	    "Name of the system this service event relates to."
	::= { cpqService3Incident 7 }

    cpqService3IncidentIPAddessOfSource OBJECT-TYPE
	SYNTAX IpAddress
	ACCESS read-only
	STATUS optional
	DESCRIPTION
	    "IP Address of the system this service event relates to."
	::= { cpqService3Incident 8 }

   cpqService3ISEEIncidentInformation OBJECT-TYPE
        SYNTAX  DisplayString (SIZE (0..255))
        ACCESS  read-only
        STATUS  mandatory
        DESCRIPTION
            "This is a URL pointing to the Service Incident status in ISEE if available."
--     This is a URL pointing to the Service Incident status if ISEE is capable of
--     providing this information. This would be an XML tag including a text field
--     identifying the status of the incident and an attached URL pointing to
--     incident information accessed via the ISEE client or the SPOP. If the ISEE
--     client can not provide this tag information, but could provide status
--     information, then the returned values would be as defined here.
        ::= { cpqService3Incident 9 }

    cpqService3IncidentIdentifier OBJECT-TYPE
        SYNTAX  DisplayString (SIZE (0..255))
        ACCESS  read-only
        STATUS  mandatory
        DESCRIPTION
            "Service Incident Identifier assigned to the incident report by the
             ISEE client."
        ::= { cpqService3Incident 10 }

    cpqService3IncidentReceiveTrapOID OBJECT-TYPE
        SYNTAX OBJECT IDENTIFIER
	ACCESS read-only
	STATUS optional
	DESCRIPTION
	    "The ID of the originally received event."
	::= { cpqService3Incident 11 }

    cpqService3IncidentFilterOID OBJECT-TYPE
        SYNTAX OBJECT IDENTIFIER
	ACCESS read-only
	STATUS deprecated
	DESCRIPTION
	    "The OID of the value that is used by the OSEM filter."
	::= { cpqService3Incident 12 }

    cpqService3IncidentFilterValue OBJECT-TYPE
	SYNTAX DisplayString (SIZE (0..255))
	ACCESS read-only
	STATUS deprecated
	DESCRIPTION
	    "The value contained in the Filter OID."
	::= { cpqService3Incident 13 }

    cpqService3RecommendedAction1 OBJECT-TYPE
        SYNTAX  DisplayString (SIZE (0..255))
        ACCESS  read-only
        STATUS  optional
        DESCRIPTION
            "Recommended action."
        ::= { cpqService3Incident 14 }

    cpqService3RecommendedAction2 OBJECT-TYPE
        SYNTAX  DisplayString (SIZE (0..255))
        ACCESS  read-only
        STATUS  optional
        DESCRIPTION
            "Recommended action continued"
        ::= { cpqService3Incident 15 }

    cpqService3RecommendedAction3 OBJECT-TYPE
        SYNTAX  DisplayString (SIZE (0..255))
        ACCESS  read-only
        STATUS  optional
        DESCRIPTION
            "Recommended action continued"
        ::= { cpqService3Incident 16 }

    cpqService3CustomerSelfRepairInstructionURL OBJECT-TYPE
        SYNTAX  DisplayString (SIZE (0..255))
        ACCESS  read-only
        STATUS  optional
        DESCRIPTION
            "A URL pointing to additional repair information"
        ::= { cpqService3Incident 17 }

    cpqService3EventSeverity OBJECT-TYPE
        SYNTAX  INTEGER {
	    critical(1),
	    major(2),
	    minor(3),
	    warning(4),
	    informational(5)
            }
        ACCESS  read-only
        STATUS  mandatory
        DESCRIPTION
            "The severity of the service incident."
        ::= { cpqService3Incident 18 }

    cpqService3AnalyzerSystemName OBJECT-TYPE
	SYNTAX DisplayString (SIZE (0..255))
	ACCESS read-only
	STATUS mandatory
	DESCRIPTION
	    "Name of the system this service event was analyzed on."
	::= { cpqService3Incident 19 }

    cpqService3FRUList1 OBJECT-TYPE
        SYNTAX  DisplayString (SIZE (0..255))
        ACCESS  read-only
        STATUS  optional
        DESCRIPTION
            "Replaceable Unit information"
        ::= { cpqService3Incident 20 }

    cpqService3FRUList2 OBJECT-TYPE
        SYNTAX  DisplayString (SIZE (0..255))
        ACCESS  read-only
        STATUS  optional
        DESCRIPTION
            "Replaceable Unit information continued"
        ::= { cpqService3Incident 21 }

    cpqService3FRUList3 OBJECT-TYPE
        SYNTAX  DisplayString (SIZE (0..255))
        ACCESS  read-only
        STATUS  optional
        DESCRIPTION
            "Replaceable Unit information continued"
        ::= { cpqService3Incident 22 }

    cpqService3FRUList4 OBJECT-TYPE
        SYNTAX  DisplayString (SIZE (0..255))
        ACCESS  read-only
        STATUS  optional
        DESCRIPTION
            "Replaceable Unit information continued"
        ::= { cpqService3Incident 23 }

    cpqService3Location1 OBJECT-TYPE
        SYNTAX  DisplayString (SIZE (0..255))
        ACCESS  read-only
        STATUS  optional
        DESCRIPTION
            "Replaceable Unit location"
        ::= { cpqService3Incident 24 }

    cpqService3Location2 OBJECT-TYPE
        SYNTAX  DisplayString (SIZE (0..255))
        ACCESS  read-only
        STATUS  optional
        DESCRIPTION
            "Replaceable Unit location continued"
        ::= { cpqService3Incident 25 }

    cpqService3Incident7Status OBJECT-TYPE

        SYNTAX  INTEGER {
            error(0),
            pending(1),
            submitted(2),
            received(3),
            open(4),
            closed(5)
            }
        ACCESS  read-only
        STATUS  mandatory
        DESCRIPTION
           "The status of the service incident for IRS 7.x."
-- adjust as desired based on implementation and remove this comment
        ::= { cpqService3Incident 26 }

   cpqService3CaseIdentifier OBJECT-TYPE
        SYNTAX  DisplayString (SIZE (0..255))
        ACCESS  read-only
        STATUS  optional
        DESCRIPTION
            "Unique Case Identifier assigned to the incident if a case is opened in the data center."
        ::= { cpqService3Incident 27 }

    cpqService3IncidentToolName OBJECT-TYPE
      SYNTAX  DisplayString (SIZE (0..255))
      ACCESS  read-only
      STATUS  mandatory
      DESCRIPTION
          "The name of the tool that is generating the trap."
      ::= { cpqService3Incident 28 }

      cpqService3IncidentToolVersion OBJECT-TYPE
        SYNTAX  DisplayString (SIZE (0..255))
        ACCESS  read-only
        STATUS  mandatory
        DESCRIPTION
            "The version of the tool that is generating the trap."
        ::= { cpqService3Incident 29 }

      cpqService3IncidentIPv6AddressOfSource OBJECT-TYPE
        SYNTAX  DisplayString (SIZE (0..255))
        ACCESS  read-only
        STATUS  optional
        DESCRIPTION
            "The IPv6 address of the source device."
        ::= { cpqService3Incident 30 }

      cpqService3IncidentSerialNumberOfSource OBJECT-TYPE
        SYNTAX  DisplayString (SIZE (0..255))
        ACCESS  read-only
        STATUS  optional
        DESCRIPTION
            "The serial number of the source device."
        ::= { cpqService3Incident 31 }

      cpqService3IncidentProductNumberOfSource OBJECT-TYPE
        SYNTAX  DisplayString (SIZE (0..255))
        ACCESS  read-only
        STATUS  optional
        DESCRIPTION
            "The product number of the source device."
        ::= { cpqService3Incident 32 }

      cpqService3IncidentProductModelOfSource OBJECT-TYPE
        SYNTAX  DisplayString (SIZE (0..255))
        ACCESS  read-only
        STATUS  optional
        DESCRIPTION
            "The product model of the source device."
        ::= { cpqService3Incident 33 }

      cpqService3IncidentUserEnteredSerialNumberOfSource OBJECT-TYPE
        SYNTAX  DisplayString (SIZE (0..255))
        ACCESS  read-only
        STATUS  optional
        DESCRIPTION
          "The user provided serial number of the source device."
        ::= { cpqService3Incident 34 }

      cpqService3IncidentUserEnteredProductNumberOfSource OBJECT-TYPE
        SYNTAX  DisplayString (SIZE (0..255))
        ACCESS  read-only
        STATUS  optional
        DESCRIPTION
          "The user provided product number of the source device."
        ::= { cpqService3Incident 35 }

      cpqService3IncidentMgmtNodeName OBJECT-TYPE
        SYNTAX  DisplayString (SIZE (0..255))
        ACCESS  read-only
        STATUS  optional
        DESCRIPTION
          "The name of the management node."
        ::= { cpqService3Incident 36 }

      cpqService3IncidentIPAddressOfMgmtNode OBJECT-TYPE
        SYNTAX  DisplayString (SIZE (0..255))
        ACCESS  read-only
        STATUS  optional
        DESCRIPTION
          "The IP address of the management node."
        ::= { cpqService3Incident 37 }

      cpqService3IncidentIPv6AddressOfMgmtNode OBJECT-TYPE
        SYNTAX  DisplayString (SIZE (0..255))
        ACCESS  read-only
        STATUS  optional
        DESCRIPTION
          "The IPv6 address of the management node."
        ::= { cpqService3Incident 38 }

      cpqService3IncidentSerialNumberOfMgmtNode OBJECT-TYPE
        SYNTAX  DisplayString (SIZE (0..255))
        ACCESS  read-only
        STATUS  optional
        DESCRIPTION
          "The serial number of the management node."
        ::= { cpqService3Incident 39 }

      cpqService3IncidentProductNumberOfMgmtNode OBJECT-TYPE
        SYNTAX  DisplayString (SIZE (0..255))
        ACCESS  read-only
        STATUS  optional
        DESCRIPTION
          "The product number of the management node."
        ::= { cpqService3Incident 40 }

      cpqService3IncidentUserEnteredSerialNumberOfMgmtNode OBJECT-TYPE
        SYNTAX  DisplayString (SIZE (0..255))
        ACCESS  read-only
        STATUS  optional
        DESCRIPTION
          "The user provided serial number of the management node."
        ::= { cpqService3Incident 41 }

      cpqService3IncidentUserEnteredProductNumberOfMgmtNode OBJECT-TYPE
        SYNTAX  DisplayString (SIZE (0..255))
        ACCESS  read-only
        STATUS  optional
        DESCRIPTION
          "The user provided product number of the management node."
        ::= { cpqService3Incident 42 }

      cpqService3IncidentProductModelOfMgmtNode OBJECT-TYPE
        SYNTAX  DisplayString (SIZE (0..255))
        ACCESS  read-only
        STATUS  optional
        DESCRIPTION
          "The product model of the management node."
        ::= { cpqService3Incident 43 }

-- ****************************************************************************
--  Service MIB Trap Definitions
--  ============================
--
--  The SNMP trap messages must not be bigger than 484 octets (bytes).
--
--  Trap support in an SNMP agent implementation is optional.  An SNMP
--  agent implementation may support all, some, or none of the traps.
--  If traps are supported, The user should be provided with the option of
--  disabling traps.
--
-- **************************************************************************

-- New in 164.00
    cpqServiceInformation TRAP-TYPE
        ENTERPRISE cpqService
        VARIABLES { sysName,
                    cpqServiceIncidentSeverity,
                    cpqServiceIncidentStatus,
                    cpqServiceIncidentInformation,
                    cpqServiceIncidentEvent,
                    cpqServiceIncidentUniqueID,
		    cpqServiceIncidentTimeofOriginalEvent,
		    cpqServiceIncidentSourceSystemName,
		    cpqServiceIncidentIPAddessOfSource,
		    cpqServiceISEEIncidentInformation,
		    cpqServiceIncidentIdentifier,
		    cpqServiceIncidentReceiveTrapOID,
		    cpqServiceIncidentFilterOID,
		    cpqServiceIncidentFilterValue }
        DESCRIPTION
            "This trap will be sent any time a service incident is logged or
             updated. A service incident is generated when it is determined that
             a service event has occurred based upon an analysis of system
             initiated event traps or an update to a service event has occurred.

             User Action: None Required"

             --#TYPE "A Service Incident has been reported (Type 1)."
             --#SUMMARY "%s reported an %s Service Incident Trap whose status is located at %s."
             --#ARGUMENTS {0, 2, 3}
--                              (the argument consists of the
--                             following:
--                             - text string containing a brief description of the
--                              event type with an associated url pointing to a
--                              description of the service event provided by
--                              OSEM/MSADB
--                            - text containing the device name with an associated
--                              URL pointing to the server agent that initiated the
--                              event.
--                            - the Event Time)
             --#SEVERITY MAJOR
             --#TIMEINDEX 18
    	       --#CATEGORY "HP Service Events"
             --#ENABLE true
             --#NOTICE_HANDLER "com.hp.mx.portal.alerts.handlers.ServiceTrapDisplayHandler"
             --#RULE_HANDLER "com.hp.mx.core.protocol.snmp.trap.components.ServiceTrapRuleHandler"

        ::= 164001

    cpqService2Information TRAP-TYPE
        ENTERPRISE cpqService
        VARIABLES { sysName,
                    cpqServiceIncidentStatus,
                    cpqServiceIncidentInformation,
                    cpqServiceIncidentEvent,
                    cpqServiceIncidentUniqueID,
		    cpqServiceIncidentTimeofOriginalEvent,
		    cpqServiceIncidentSourceSystemName,
		    cpqServiceIncidentIPAddessOfSource,
		    cpqServiceISEEIncidentInformation,
		    cpqServiceIncidentIdentifier,
		    cpqServiceIncidentReceiveTrapOID,
		    cpqServiceRecommendedAction1,
		    cpqServiceRecommendedAction2,
		    cpqServiceRecommendedAction3,
		    cpqServiceCustomerSelfRepairInstructionURL }
        DESCRIPTION
            "This event will be sent any time a service incident is reported.
             A service incident is generated when it is determined that a serviceable
             event has occurred based upon analysis of system-initiated events.

             User Action: Refer to the Recommended Action section under the event details section"

             --#TYPE "A Service Incident has been reported (Type 2)."
             --#SUMMARY "%s reported a Service Incident Trap whose status is located at %s."
             --#ARGUMENTS {0, 1}
--                              (the argument consists of the
--                             following:
--                             - text string containing a brief description of the
--                              event type with an associated url pointing to a
--                              description of the service event provided by
--                              OSEM/MSADB
--                            - text containing the device name with an associated
--                              URL pointing to the server agent that initiated the
--                              event.
--                            - the Event Time)
             --#SEVERITY MAJOR
             --#TIMEINDEX 18
	       --#CATEGORY "HP Service Events"
             --#ENABLE true
             --#NOTICE_HANDLER "com.hp.mx.portal.alerts.handlers.ServiceTrapDisplayHandler"
             --#RULE_HANDLER "com.hp.mx.core.protocol.snmp.trap.components.ServiceTrapRuleHandler"
        ::= 164002

    cpqService3Information TRAP-TYPE
        ENTERPRISE cpqService
        VARIABLES { cpqService3IncidentSourceSystemName,
		    cpqService3IncidentIPAddessOfSource,
		    cpqService3EventSeverity,
                    cpqService3IncidentStatus,
                    cpqService3IncidentInformation,
                    cpqService3IncidentEvent,
                    cpqService3IncidentUniqueID,
		    cpqService3IncidentTimeofOriginalEvent,
                    cpqService3AnalyzerSystemName,
		    cpqService3ISEEIncidentInformation,
		    cpqService3IncidentIdentifier,
		    cpqService3IncidentReceiveTrapOID,
		    cpqService3RecommendedAction1,
		    cpqService3RecommendedAction2,
		    cpqService3RecommendedAction3,
		    cpqService3FRUList1,
		    cpqService3FRUList2,
	            cpqService3FRUList3,
		    cpqService3FRUList4,
                    cpqService3Location1,
                    cpqService3Location2,
		    cpqService3CustomerSelfRepairInstructionURL }
        DESCRIPTION
            "This event will be sent any time a service incident is reported.
             A service incident is generated when it is determined that a serviceable
             event has occurred based upon analysis of system-initiated events.

             User Action: Refer to the Recommended Action section under the event details section"

             --#TYPE "A Service Incident has been reported (Type 3)."
             --#SUMMARY "%s reported a Service Incident Trap whose status is located at %s."
             --#ARGUMENTS {0, 4}
--                              (the argument consists of the
--                             following:
--                             - text string containing a brief description of the
--                              event type with an associated url pointing to a
--                              description of the service event provided by
--                              OSEM/MSADB
--                            - text containing the device name with an associated
--                              URL pointing to the server agent that initiated the
--                              event.
--                            - the Event Time)
             --#SEVERITY MAJOR
             --#TIMEINDEX 18
	     --#CATEGORY "HP Service Events"
             --#ENABLE true
	     --#VARBINDSEVERITY 3
             --#SEVERITYMAP "INFORMATIONAL = INFORMATIONAL, MINOR = MINOR, WARNING = WARNING, MAJOR = MAJOR, CRITICAL = CRITICAL,5 = INFORMATIONAL, 4 = WARNING, 3=MINOR, 2 = MAJOR, 1 = CRITICAL"
             --#NOTICE_HANDLER "com.hp.mx.portal.alerts.handlers.ServiceTrapDisplayHandler"
             --#RULE_HANDLER "com.hp.mx.core.protocol.snmp.trap.components.ServiceTrapRuleHandler"

        ::= 164003

--     This Trap presents CpqServiceIncidentSeverity as an XML Tag including a text
--     description as described within the varbind definition and
--     CpqServiceIncidentInformation as a hidden URL pointing to
--     the Service Rule describing the serviceable event (OSEM).
--     This Trap presents cpqServiceIncidentStatus as an XML tag including a text
--     field identifying the originating status of the incident and
--     CpqServiceIncidentStatus an a hidden URL pointing to incident information
--     accessed via the ISEE client or the SPOP.
--     If the ISEE client can not provide this tag information, but could provide
--     status information, then the returned values would be as defined within the
--     varbind definition.

    cpqService4Information TRAP-TYPE
        ENTERPRISE cpqService
        VARIABLES { cpqService3IncidentSourceSystemName,
		cpqService3IncidentIPAddessOfSource,
		cpqService3EventSeverity,
		cpqService3Incident7Status,
		cpqService3IncidentInformation,
		cpqService3IncidentEvent,
		cpqService3IncidentUniqueID,
		cpqService3IncidentTimeofOriginalEvent,
		cpqService3AnalyzerSystemName,
		cpqService3ISEEIncidentInformation,
		cpqService3IncidentIdentifier,
		cpqService3CaseIdentifier,
		cpqService3IncidentReceiveTrapOID,
		cpqService3RecommendedAction1,
		cpqService3RecommendedAction2,
		cpqService3RecommendedAction3,
		cpqService3FRUList1,
		cpqService3FRUList2,
	        cpqService3FRUList3,
		cpqService3FRUList4,
		cpqService3Location1,
		cpqService3Location2,
		cpqService3CustomerSelfRepairInstructionURL }
        DESCRIPTION
            "This event will be sent any time a service incident is reported.
             A service incident is generated when it is determined that a serviceable
             event has occurred based upon analysis of system-initiated events.

             User Action: Refer to the Recommended Action section under the event details section"

             --#TYPE "A Service Incident has been reported (Type 4)."
             --#SUMMARY "%s reported a Service Incident Trap whose status is %s."
             --#ARGUMENTS {0, 3}
--                              (the argument consists of the
--                             following:
--                             - text string containing a brief description of the
--                              event type with an associated url pointing to a
--                              description of the service event provided by
--                              OSEM/MSADB
--                            - text containing the device name with an associated
--                              URL pointing to the server agent that initiated the
--                              event.
--                            - the Event Time)
             --#SEVERITY MAJOR
             --#TIMEINDEX 18
	     --#CATEGORY "HP Service Events"
             --#ENABLE true
	     --#VARBINDSEVERITY 3
             --#SEVERITYMAP "INFORMATIONAL = INFORMATIONAL, MINOR = MINOR, WARNING = WARNING, MAJOR = MAJOR, CRITICAL = CRITICAL,5 = INFORMATIONAL, 4 = WARNING, 3=MINOR, 2 = MAJOR, 1 = CRITICAL"
             --#NOTICE_HANDLER "com.hp.mx.portal.alerts.handlers.ServiceTrapDisplayHandler"
             --#RULE_HANDLER "com.hp.mx.core.protocol.snmp.trap.components.ServiceTrapRuleHandler"

        ::= 164004

        --     This Trap presents CpqServiceIncidentSeverity as an XML Tag including a text
        --     description as described within the varbind definition and
        --     CpqServiceIncidentInformation as a hidden URL pointing to
        --     the Service Rule describing the serviceable event (OSEM).
        --     This Trap presents cpqServiceIncidentStatus as an XML tag including a text
        --     field identifying the originating status of the incident and
        --     CpqServiceIncidentStatus an a hidden URL pointing to incident information
        --     accessed via the ISEE client or the SPOP.
        --     If the ISEE client can not provide this tag information, but could provide
        --     status information, then the returned values would be as defined within the
        --     varbind definition.

            cpqService5Information TRAP-TYPE
                ENTERPRISE cpqService
                VARIABLES { cpqService3IncidentSourceSystemName,
        		cpqService3IncidentIPAddessOfSource,
        		cpqService3EventSeverity,
        		cpqService3Incident7Status,
        		cpqService3IncidentInformation,
        		cpqService3IncidentEvent,
        		cpqService3IncidentUniqueID,
        		cpqService3IncidentTimeofOriginalEvent,
        		cpqService3AnalyzerSystemName,
        		cpqService3ISEEIncidentInformation,
        		cpqService3IncidentIdentifier,
        		cpqService3CaseIdentifier,
        		cpqService3IncidentReceiveTrapOID,
        		cpqService3RecommendedAction1,
        		cpqService3RecommendedAction2,
        		cpqService3RecommendedAction3,
        		cpqService3FRUList1,
        		cpqService3FRUList2,
        	  cpqService3FRUList3,
        		cpqService3FRUList4,
        		cpqService3Location1,
        		cpqService3Location2,
        		cpqService3CustomerSelfRepairInstructionURL,
            cpqService3IncidentToolName,
            cpqService3IncidentToolVersion,
            cpqService3IncidentIPv6AddressOfSource,
            cpqService3IncidentSerialNumberOfSource,
            cpqService3IncidentProductNumberOfSource,
            cpqService3IncidentProductModelOfSource,
            cpqService3IncidentUserEnteredSerialNumberOfSource,
            cpqService3IncidentUserEnteredProductNumberOfSource,
            cpqService3IncidentMgmtNodeName,
            cpqService3IncidentIPAddressOfMgmtNode,
            cpqService3IncidentIPv6AddressOfMgmtNode,
            cpqService3IncidentSerialNumberOfMgmtNode,
            cpqService3IncidentProductNumberOfMgmtNode,
            cpqService3IncidentUserEnteredSerialNumberOfMgmtNode,
            cpqService3IncidentUserEnteredProductNumberOfMgmtNode,
            cpqService3IncidentProductModelOfMgmtNode }
                DESCRIPTION
                    "This event will be sent any time a service incident is reported.
                     A service incident is generated when it is determined that a serviceable
                     event has occurred based upon analysis of system-initiated events.

                     User Action: Refer to the Recommended Action section under the event details section"

                     --#TYPE "A Service Incident has been reported (Type 5)."
                     --#SUMMARY "%s reported a Service Incident Trap whose status is %s."
                     --#ARGUMENTS {0, 3}
        --                              (the argument consists of the
        --                             following:
        --                            - Text containing name of the system this service event relates to.
        --                            - The status of the service incident for IRS 7.x.)
                     --#SEVERITY MAJOR
                     --#TIMEINDEX 18
        	     --#CATEGORY "HP Service Events"
                     --#ENABLE true
        	     --#VARBINDSEVERITY 3
                     --#SEVERITYMAP "INFORMATIONAL = INFORMATIONAL, MINOR = MINOR, WARNING = WARNING, MAJOR = MAJOR, CRITICAL = CRITICAL,5 = INFORMATIONAL, 4 = WARNING, 3=MINOR, 2 = MAJOR, 1 = CRITICAL"
                     --#NOTICE_HANDLER "com.hp.mx.portal.alerts.handlers.ServiceTrapDisplayHandler"
                     --#RULE_HANDLER "com.hp.mx.core.protocol.snmp.trap.components.ServiceTrapRuleHandler"

                ::= 164005

END
