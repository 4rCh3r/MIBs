-- 
-- Dell Remote Access Controller (RAC) and Chassis Management Controller (CMC)
-- Management Information Base
--
-- This MIB is the legacy iDRAC MIB.  Changes are no longer made to this MIB
-- for iDRACs.  iDRACs don't support all of the objects and traps defined
-- in this MIB.  There is a new and more extensive iDRAC MIB available for
-- newer iDRACs (iDRAC7 and newer).
--
-- This MIB is also the CMC MIB.  Changes are made to this MIB only for CMCs now.
--
-- Copyright (c) 2016 Dell Inc.
--
-- Last Changed Revision: 19
-- Last Changed Date: 2016-04-23 23:46:06 -0530 (Sat, 23 Apr 2016)
-- Text Last Updated: 2016-04-23 23:46:06 -0530 (Sat, 23 Apr 2016)
--

DELL-RAC-MIB DEFINITIONS ::= BEGIN
     
IMPORTS
	enterprises, TimeTicks
		FROM RFC1155-SMI
	OBJECT-TYPE
		FROM RFC-1212
	TRAP-TYPE
		FROM RFC-1215
	DisplayString
		FROM RFC1213-MIB;

-- text convention ------------------------------------------------------------------------     

	-------------------------------------------------------------------------------
	-- This data type is used to model textual information taken
	-- from the NVT ASCII character set.  By convention, objects
	-- with this syntax are declared as having
	--      SIZE (0..1023)
	-------------------------------------------------------------------------------
	DellString ::= DisplayString (SIZE (0..1023))

	DellRacType ::= INTEGER
	{
		other(1),               -- the DRAC type is not one of the following
		unknown(2),             -- the DRAC type is unknown
		dracIII(3),             -- Drac III
		era(4),                 -- ERA
		drac4(5),               -- Drac 4
		drac5(6),               -- Drac 5
		drac5MC(7),             -- Drac 5/MC
		cmc(8),                 -- CMC
		idrac(9),               -- iDRAC
		idrac7monolithic(16),   -- iDRAC7 Monolithic
		idrac7modular(17),      -- iDRAC7 Modular
		vrtxCMC(18),            -- VRTX CMC
		fx2CMC(19),             -- FX2 Family CMC
		idrac8monolithic(32),   -- iDRAC8 Monolithic
		idrac8modular(33)       -- iDRAC8 Modular
	}

	DellStatus ::= INTEGER
	{
		other(1),               -- the status of the object is not one of the following:
		unknown(2),             -- the status of the object is unknown
										--  (not known or monitored)
		ok(3),                  -- the status of the object is ok
		nonCritical(4),         -- the status of the object is warning, non-critical
		critical(5),            -- the status of the object is critical (failure)
		nonRecoverable(6)       -- the status of the object is non-recoverable (dead)
	}

	-------------------------------------------------------------------------------
	-- DellPowerReading is a string representation of a floating point value, 
	--   having exactly 3 digits of precision, and a maximum of 31 characters.
	--
	-- DellChassisPowerIndexRange defines the possible chassis power instances
	--   in this MIB.
	--
	-- DellCMCPSUIndexRange defines the possible CMC Power Supply Unit (PSU) 
	--   instances, per chassis power instance, in this MIB.
	--
	-- DellCMCPSUCapable is an enumeration of PSU presence and/or monitoring 
	--   capabilities.
	--
	-- DellTemperatureReading is an integer value, expressed in degrees Celsius.
	-------------------------------------------------------------------------------
	DellPowerReading ::= DisplayString (SIZE (0..32))

	DellCMCPowerIndexRange ::= INTEGER (1..1)

	DellCMCPSUIndexRange ::= INTEGER (1..6)

	DellCMCPSUCapable ::= INTEGER
	{
		absent(1),      -- power supply is not present
		none(2),        -- no power monitoring abilities
		basic(3)        -- basic power monitoring abilities
	}

	DellTemperatureReading ::= INTEGER

	-------------------------------------------------------------------------------
	-- DellTimestamp is defined in the displayable format:
	--
	--			yyyymmddHHMMSS.uuuuuuDooo
	--
	-- where yyyy is the year, mm is the month number, dd is the day of the month,
	-- HHMMSS are the hours, minutes and seconds, respectively, uuuuuu is the
	-- number of microseconds, D is the UTC offset direction, and ooo is the 
	-- offset from UTC, in minutes. 
	--
	-- Note: D is a plus (+) sign if east of UTC, and a minus (-) if west of UTC.
	--
	-- For example, Wednesday, May 25, 1994, at 1:30:15 PM EDT
	--   would be represented as: 19940525133015.000000-300
	-------------------------------------------------------------------------------
	DellTimestamp ::= DisplayString (SIZE (26))

	-------------------------------------------------------------------------------
	-- DellCMCServerIndexRange defines the possible chassis server instances
	--   in this MIB.
	--
	-- DellCMCServerCapable is an enumeration of server presence and/or monitoring 
	--   capabilities.
	-------------------------------------------------------------------------------
	DellCMCServerIndexRange ::= INTEGER (1..32)

	DellCMCServerCapable ::= INTEGER
	{
		absent(1),      -- server is not present
		none(2),        -- no server monitoring abilities
		basic(3),       -- basic server monitoring abilities
		off(4)          -- server is powered off
	}

	DellCMCServerStorageMode ::= INTEGER
	{
		notApplicable(1),    -- not applicable to server
		joined(2),           -- storage mode is Joined
		splitDualHost(3),    -- storage mode is Split Dual Host
		splitSingleHost(4),  -- storage mode is Split Single Host
		unknown(99)          -- storage mode is unknown
	}

	DellCMCServerIntrusionState ::= INTEGER
	{
		notApplicable(1),    -- not applicable to server
		closed(2),           -- intrusion state is Closed
		open(3),             -- intrusion state is Open
		unknown(99)          -- intrusion state is unknown
	}


-- MIB Objects and Tables --------------------------------------------------------

	dell                          OBJECT IDENTIFIER ::= { enterprises    674   }
	server3                       OBJECT IDENTIFIER ::= { dell           10892 }
	drsOutofBandGroup             OBJECT IDENTIFIER ::= { server3        2     }
	drsInformationGroup           OBJECT IDENTIFIER ::= { drsOutofBandGroup     1 }
	drsProductInfoGroup           OBJECT IDENTIFIER ::= { drsInformationGroup   1 }
	drsFirmwareGroup              OBJECT IDENTIFIER ::= { drsInformationGroup   2 }

	drsStatusGroup                OBJECT IDENTIFIER ::= { drsOutofBandGroup     2 }

	drsChassisStatusGroup         OBJECT IDENTIFIER ::= { drsOutofBandGroup     3 }
	drsStatusNowGroup             OBJECT IDENTIFIER ::= { drsChassisStatusGroup 1 }
	drsStatusPrevGroup            OBJECT IDENTIFIER ::= { drsChassisStatusGroup 2 }
	drsStatusChangeGroup          OBJECT IDENTIFIER ::= { drsChassisStatusGroup 3 }

	drsChassisPowerGroup          OBJECT IDENTIFIER ::= { drsOutofBandGroup     4 }

		DrsCMCPowerTableEntry ::= SEQUENCE
		{
			drsChassisIndex				DellCMCPowerIndexRange,
			drsPotentialPower				DellPowerReading,
			drsIdlePower					DellPowerReading,
			drsMaxPowerSpecification	DellPowerReading,
			drsPowerSurplus				DellPowerReading,
			drsKWhCumulative				DellPowerReading,
			drsKWhCumulativeTime			DellTimestamp,
			drsWattsPeakUsage				DellPowerReading,
			drsWattsPeakTime				DellTimestamp,
			drsWattsMinUsage				DellPowerReading,
			drsWattsMinTime				DellTimestamp,
			drsWattsResetTime				DellTimestamp,
			drsWattsReading				DellPowerReading,
			drsAmpsReading					DellPowerReading
		}

		DrsCMCPSUTableEntry ::= SEQUENCE
		{
			drsPSUChassisIndex			DellCMCPowerIndexRange,
			drsPSUIndex						DellCMCPSUIndexRange,
			drsPSULocation					DellString,
			drsPSUMonitoringCapable		DellCMCPSUCapable,
			drsPSUVoltsReading			DellPowerReading,
			drsPSUAmpsReading				DellPowerReading,
			drsPSUWattsReading			DellPowerReading
		}

	drsChassisServerGroup         OBJECT IDENTIFIER ::= { drsOutofBandGroup     5 }

		DrsCMCServerTableEntry ::= SEQUENCE
		{
			drsServerIndex				DellCMCServerIndexRange,
			drsServerMonitoringCapable  DellCMCServerCapable,
			drsServerServiceTag			DellString,
			drsServerSlotName			DellString,
			drsServerSlotNumber			DellString,
			drsServerNodeID				DellString,
			drsServerModel				DellString,
			drsServerAssetTag			DellString,
			drsServerNumStorageControllers	INTEGER,
			drsServerStorageMode        DellCMCServerStorageMode,
			drsServerIntrusionState     DellCMCServerIntrusionState,
			drsServerAssignedServerSlots  DellString
		}

-- Storage details start
storageDetailsGroup             OBJECT IDENTIFIER ::= { drsOutofBandGroup 6      }
software                        OBJECT IDENTIFIER ::= { storageDetailsGroup 1 }
storageManagement               OBJECT IDENTIFIER ::= { software 20           }
physicalDevices                 OBJECT IDENTIFIER ::= { storageManagement 130 }
logicalDevices                  OBJECT IDENTIFIER ::= { storageManagement 140 }


------------------------------------------------------------------------------
-- Textual Conventions
------------------------------------------------------------------------------

FQDDString                      ::= DisplayString (SIZE (0..512))

ObjectStatusEnum        ::= INTEGER {
    other(1),           -- the status of the object is not one of the
                        --  following:
    unknown(2),         -- the status of the object is unknown
                        --  (not known or monitored)
    ok(3),              -- the status of the object is ok
    nonCritical(4),     -- the status of the object is warning, non-critical
    critical(5),        -- the status of the object is critical (failure)
    nonRecoverable(6)   -- the status of the object is non-recoverable (dead)
}
BooleanType                     ::= INTEGER (0..1)    -- 0 = FALSE, 1 = TRUE


-- Storage details end


	drsCMCAlertGroup              OBJECT IDENTIFIER ::= { drsOutofBandGroup    20 }
	drsChassisAlertVariables      OBJECT IDENTIFIER ::= { drsCMCAlertGroup     10 }
	drsCMCAlert2Group             OBJECT IDENTIFIER ::= { drsOutofBandGroup    21 }
	drsChassisAlert2Variables     OBJECT IDENTIFIER ::= { drsCMCAlert2Group    10 }

	drsAlertGroup                 OBJECT IDENTIFIER ::= { drsOutofBandGroup  5000 }
	drsAlertVariables             OBJECT IDENTIFIER ::= { drsAlertGroup        10 }
        

-- Variables and Traps ------------------------------------------------------------------------

	-------------------------------------------------------------------------------
	-- group: product information
	-------------------------------------------------------------------------------

	drsProductName      OBJECT-TYPE
		SYNTAX          DellString
		ACCESS          read-only
		STATUS          mandatory
		DESCRIPTION     "0001.0001.0001 This attribute defines the product name of a chassis management controller." 
			::= { drsProductInfoGroup 1 }

	drsProductShortName OBJECT-TYPE
		SYNTAX          DellString
		ACCESS          read-only
		STATUS          mandatory
		DESCRIPTION     "0001.0001.0002 This attribute defines the short product name of a chassis management controller. " 
			::= { drsProductInfoGroup 2 }

	drsProductDescription OBJECT-TYPE
		SYNTAX          DellString
		ACCESS          read-only
		STATUS          mandatory
		DESCRIPTION     "0001.0001.0003 This attribute defines the product description of a chassis management controller. " 
			::= { drsProductInfoGroup 3 }

	drsProductManufacturer OBJECT-TYPE
		SYNTAX          DellString
		ACCESS          read-only
		STATUS          mandatory
		DESCRIPTION     "0001.0001.0004 This attribute defines the product manufacturer of a chassis management controller. " 
			::= { drsProductInfoGroup 4 }

	drsProductVersion OBJECT-TYPE
		SYNTAX          DellString
		ACCESS          read-only
		STATUS          mandatory
		DESCRIPTION     "0001.0001.0005 This attribute defines the product version of a chassis management controller. " 
			::= { drsProductInfoGroup 5 }

	drsChassisServiceTag OBJECT-TYPE
		SYNTAX          DellString
		ACCESS          read-only
		STATUS          mandatory
		DESCRIPTION     "0001.0001.0007 This attribute defines the Service Tag of the chassis. " 
			::= { drsProductInfoGroup 6 }

	drsProductURL       OBJECT-TYPE
		SYNTAX          DellString 
		ACCESS          read-only
		STATUS          mandatory
		DESCRIPTION     "0001.0001.0006 This attribute defines the out-of-band UI URL of a chassis management controller. "
			::= { drsProductInfoGroup 7 }
                        
	drsProductChassisAssetTag  OBJECT-TYPE
		SYNTAX          DellString 
		ACCESS          read-only
		STATUS          mandatory
		DESCRIPTION     "0001.0001.0008 This attribute defines the Asset Tag of the chassis. "
			::= { drsProductInfoGroup 8 }

	drsProductChassisLocation  OBJECT-TYPE
		SYNTAX          DellString 
		ACCESS          read-only
		STATUS          mandatory
		DESCRIPTION     "0001.0001.0009 This attribute defines the location of the chassis. "
			::= { drsProductInfoGroup 9 }

	drsProductChassisName  OBJECT-TYPE
		SYNTAX          DellString 
		ACCESS          read-only
		STATUS          mandatory
		DESCRIPTION     "0001.0001.0010 This attribute defines the name of the chassis. "
			::= { drsProductInfoGroup 10 }

	drsSystemServiceTag  OBJECT-TYPE
		SYNTAX          DellString 
		ACCESS          read-only
		STATUS          mandatory
		DESCRIPTION     "0001.0001.0011 This attribute defines the service tag of a system. "
			::= { drsProductInfoGroup 11 }

	drsProductSystemAssetTag  OBJECT-TYPE
		SYNTAX          DellString 
		ACCESS          read-only
		STATUS          mandatory
		DESCRIPTION     "0001.0001.0012 This attribute defines the asset tag of a system. "
			::= { drsProductInfoGroup 12 }

	drsProductSystemSlot OBJECT-TYPE
		SYNTAX          DellString 
		ACCESS          read-only
		STATUS          mandatory
		DESCRIPTION     "0001.0001.0013 This attribute defines the slot number of a CMC. "
			::= { drsProductInfoGroup 13 }

	drsProductType  OBJECT-TYPE
		SYNTAX          DellRacType
		ACCESS          read-only
		STATUS          mandatory
		DESCRIPTION     "0001.0001.0014 This attribute defines type of a remote access card "
			::= { drsProductInfoGroup 14 }
               
	drsProductChassisDataCenter  OBJECT-TYPE
		SYNTAX          DellString 
		ACCESS          read-only
		STATUS          mandatory
		DESCRIPTION     "0001.0001.0015 This attribute defines the Data Center locator of the chassis. "
			::= { drsProductInfoGroup 15 }

	drsProductChassisAisle  OBJECT-TYPE
		SYNTAX          DellString 
		ACCESS          read-only
		STATUS          mandatory
		DESCRIPTION     "0001.0001.0016 This attribute defines the Aisle locator of the chassis. "
			::= { drsProductInfoGroup 16 }

	drsProductChassisRack  OBJECT-TYPE
		SYNTAX          DellString 
		ACCESS          read-only
		STATUS          mandatory
		DESCRIPTION     "0001.0001.0017 This attribute defines the Rack locator of the chassis. "
			::= { drsProductInfoGroup 17 }

	drsProductChassisRackSlot  OBJECT-TYPE
		SYNTAX          DellString 
		ACCESS          read-only
		STATUS          mandatory
		DESCRIPTION     "0001.0001.0018 This attribute defines the Rack Slot locator of the chassis. "
			::= { drsProductInfoGroup 18 }
               
	drsProductChassisModel  OBJECT-TYPE
		SYNTAX          DellString
		ACCESS          read-only
		STATUS          mandatory
		DESCRIPTION     "0001.0001.0019 This attribute defines the Model of the chassis."
			::= { drsProductInfoGroup 19 }
               
	drsProductChassisExpressServiceCode  OBJECT-TYPE
		SYNTAX          DellString
		ACCESS          read-only
		STATUS          mandatory
		DESCRIPTION     "0001.0001.0020 This attribute defines the Express Service Code of the chassis."
			::= { drsProductInfoGroup 20 }
               
	drsProductChassisSystemID  OBJECT-TYPE
		SYNTAX          INTEGER
		ACCESS          read-only
		STATUS          mandatory
		DESCRIPTION     "0001.0001.0021 This attribute defines the System ID of the chassis."
			::= { drsProductInfoGroup 21 }
               
	drsProductChassisSize  OBJECT-TYPE
		SYNTAX          INTEGER
		ACCESS          read-only
		STATUS          mandatory
		DESCRIPTION     "0001.0001.0022 This attribute defines the size of the
						chassis in rack units (U).  A U is a standard unit of
						measure for the height of a rack or rack-mountable component."
			::= { drsProductInfoGroup 22 }

	-------------------------------------------------------------------------------
	-- group: firmware
	-------------------------------------------------------------------------------

	drsFirmwareVersion  OBJECT-TYPE
		SYNTAX          DellString
		ACCESS          read-only
		STATUS          mandatory
		DESCRIPTION     "0001.0002.0001 This attribute defines the firmware version of chassis management controller 1."
			::= { drsFirmwareGroup 1 }

	drsiKVMFirmwareVersion  OBJECT-TYPE
		SYNTAX          DellString
		ACCESS          read-only
		STATUS          mandatory
		DESCRIPTION     "0001.0002.0002 This attribute defines the firmware version of the iKVM. " 
			::= { drsFirmwareGroup 2 }

	drsFirmwareVersion2 OBJECT-TYPE
		SYNTAX          DellString
		ACCESS          read-only
		STATUS          mandatory
		DESCRIPTION     "0001.0002.0003 This attribute defines the firmware version of chassis management controller 2."
			::= { drsFirmwareGroup 3 }

	-------------------------------------------------------------------------------
	-- group: chassis status
	-------------------------------------------------------------------------------

	drsGlobalSystemStatus OBJECT-TYPE
		SYNTAX          DellStatus
		ACCESS          read-only
		STATUS          mandatory
		DESCRIPTION     "0002.0001.0001 This attribute defines the overall chassis status
                      being monitored by the chassis management card." 
			::= { drsStatusGroup 1 }

	drsGlobalCurrStatus OBJECT-TYPE
		SYNTAX          DellStatus
		ACCESS          read-only
		STATUS          mandatory
		DESCRIPTION     "0003.0001.0001 This attribute defines the overall chassis status
                      being monitored by the chassis management card." 
			::= { drsStatusNowGroup 1 }

	drsIOMCurrStatus  OBJECT-TYPE
		SYNTAX          DellStatus
		ACCESS          read-only
		STATUS          mandatory
		DESCRIPTION     "0003.0001.0002 This attribute defines the IOM subsystem status
                      being monitored by the chassis management card." 
			::= { drsStatusNowGroup 2 }

	drsKVMCurrStatus  OBJECT-TYPE
		SYNTAX          DellStatus
		ACCESS          read-only
		STATUS          mandatory
		DESCRIPTION     "0003.0001.0003 This attribute defines the iKVM subsystem health status
                      being monitored by the chassis management card." 
			::= { drsStatusNowGroup 3 }

	drsRedCurrStatus  OBJECT-TYPE
		SYNTAX          DellStatus
		ACCESS          read-only
		STATUS          mandatory
		DESCRIPTION     "0003.0001.0004 This attribute defines the Redundancy status
                      being monitored by the chassis management card." 
			::= { drsStatusNowGroup 4 }

	drsPowerCurrStatus OBJECT-TYPE
		SYNTAX          DellStatus
		ACCESS          read-only
		STATUS          mandatory
		DESCRIPTION     "0003.0001.0005 This attribute defines the power subsystem health status
                      being monitored by the chassis management card." 
			::= { drsStatusNowGroup 5 }

	drsFanCurrStatus OBJECT-TYPE
		SYNTAX          DellStatus
		ACCESS          read-only
		STATUS          mandatory
		DESCRIPTION     "0003.0001.0006 This attribute defines the Fan subsystem health status
                      being monitored by the chassis management card." 
			::= { drsStatusNowGroup 6 }

	drsBladeCurrStatus OBJECT-TYPE
		SYNTAX          DellStatus
		ACCESS          read-only
		STATUS          mandatory
		DESCRIPTION     "0003.0001.0007 This attribute defines the Blade subsystem health status
                      being monitored by the chassis management card." 
			::= { drsStatusNowGroup 7 }

	drsTempCurrStatus OBJECT-TYPE
		SYNTAX          DellStatus
		ACCESS          read-only
		STATUS          mandatory
		DESCRIPTION     "0003.0001.0008 This attribute defines the Temp Sensor subsystem health status
                      being monitored by the chassis management card." 
			::= { drsStatusNowGroup 8 }

	drsCMCCurrStatus OBJECT-TYPE
		SYNTAX          DellStatus
		ACCESS          read-only
		STATUS          mandatory
		DESCRIPTION     "0003.0001.0009 This attribute defines the CMC health status
                      being monitored by the chassis management card." 
			::= { drsStatusNowGroup 9 }

	drsChassisFrontPanelAmbientTemperature OBJECT-TYPE
		SYNTAX          DellTemperatureReading
		ACCESS          read-only
		STATUS          mandatory
		DESCRIPTION     "0003.0001.0010 This attribute defines the ambient temperature
                      reading (in degrees Celsius) for the chassis front panel controller." 
			::= { drsStatusNowGroup 10 }

	drsCMCAmbientTemperature OBJECT-TYPE
		SYNTAX          DellTemperatureReading
		ACCESS          read-only
		STATUS          mandatory
		DESCRIPTION     "0003.0001.0011 This attribute defines the ambient temperature
                      reading (in degrees Celsius) for the chassis management card." 
			::= { drsStatusNowGroup 11 }

	drsCMCProcessorTemperature OBJECT-TYPE
		SYNTAX          DellTemperatureReading
		ACCESS          read-only
		STATUS          mandatory
		DESCRIPTION     "0003.0001.0012 This attribute defines the temperature reading
                      (in degrees Celsius) for the chassis management card processor." 
			::= { drsStatusNowGroup 12 }

	drsGlobalPrevStatus OBJECT-TYPE
		SYNTAX          DellStatus
		ACCESS          read-only
		STATUS          mandatory
		DESCRIPTION     "0003.0002.0001 This attribute defines the previous chassis status
                      recorded by the chassis management card." 
			::= { drsStatusPrevGroup 1 }
                
	drsIOMPrevStatus    OBJECT-TYPE
		SYNTAX          DellStatus
		ACCESS          read-only
		STATUS          mandatory
		DESCRIPTION     "0003.0002.0002 This attribute defines the previous IOM subsystem status
                      recorded by the chassis management card." 
			::= { drsStatusPrevGroup 2 }

	drsKVMPrevStatus    OBJECT-TYPE
		SYNTAX          DellStatus
		ACCESS          read-only
		STATUS          mandatory
		DESCRIPTION     "0003.0002.0003 This attribute defines the previous iKVM subsystem health status
                      recorded by the chassis management card." 
			::= { drsStatusPrevGroup 3 }

	drsRedPrevStatus    OBJECT-TYPE
		SYNTAX          DellStatus
		ACCESS          read-only
		STATUS          mandatory
		DESCRIPTION     "0003.0002.0004 This attribute defines the previous Redundancy status
                      recorded by the chassis management card." 
			::= { drsStatusPrevGroup 4 }

	drsPowerPrevStatus  OBJECT-TYPE
		SYNTAX          DellStatus
		ACCESS          read-only
		STATUS          mandatory
		DESCRIPTION     "0003.0002.0005 This attribute defines the previous power subsystem health status
                      recorded by the chassis management card." 
			::= { drsStatusPrevGroup 5 }

	drsFanPrevStatus OBJECT-TYPE
		SYNTAX          DellStatus
		ACCESS          read-only
		STATUS          mandatory
		DESCRIPTION     "0003.0002.0006 This attribute defines the previous Fan health status
                      being monitored by the chassis management card." 
			::= { drsStatusPrevGroup 6 }

	drsBladePrevStatus  OBJECT-TYPE
		SYNTAX          DellStatus
		ACCESS          read-only
		STATUS          mandatory
		DESCRIPTION     "0003.0002.0007 This attribute defines the previous Blade subsystem health status
                      recorded by the chassis management card." 
			::= { drsStatusPrevGroup 7 }

	drsTempPrevStatus OBJECT-TYPE
		SYNTAX          DellStatus
		ACCESS          read-only
		STATUS          mandatory
		DESCRIPTION     "0003.0001.0008 This attribute defines the Temp Sensor health status
                      being monitored by the chassis management card." 
			::= { drsStatusPrevGroup 8 }

	drsCMCPrevStatus OBJECT-TYPE
		SYNTAX          DellStatus
		ACCESS          read-only
		STATUS          mandatory
		DESCRIPTION     "0003.0001.0009 This attribute defines the CMC health status
                      being monitored by the chassis management card." 
			::= { drsStatusPrevGroup 9 }

	drsGlobalChangeTime OBJECT-TYPE
		SYNTAX          TimeTicks
		ACCESS          read-only
		STATUS          mandatory
		DESCRIPTION     "0003.0003.0001 This attribute defines the timestamp of the most recent 
                      global status change." 
			::= { drsStatusChangeGroup 1 }

	drsIOMChangeTime    OBJECT-TYPE
		SYNTAX          TimeTicks
		ACCESS          read-only
		STATUS          mandatory
		DESCRIPTION     "0003.0003.0002 This attribute defines the timestamp of the most recent 
                      IOM status change." 
			::= { drsStatusChangeGroup 2 }

	drsKVMChangeTime    OBJECT-TYPE
		SYNTAX          TimeTicks
		ACCESS          read-only
		STATUS          mandatory
		DESCRIPTION     "0003.0003.0003 This attribute defines the timestamp of the most recent 
                      iKVM status change." 
			::= { drsStatusChangeGroup 3 }

	drsRedChangeTime    OBJECT-TYPE
		SYNTAX          TimeTicks
		ACCESS          read-only
		STATUS          mandatory
		DESCRIPTION     "0003.0003.0004 This attribute defines the timestamp of the most recent 
                      Redundancy status change." 
			::= { drsStatusChangeGroup 4 }

	drsPowerChangeTime  OBJECT-TYPE
		SYNTAX          TimeTicks
		ACCESS          read-only
		STATUS          mandatory
		DESCRIPTION     "0003.0003.0005 This attribute defines the timestamp of the most recent 
                      power health status change." 
			::= { drsStatusChangeGroup 5 }

	drsFanChangeTime OBJECT-TYPE
		SYNTAX          TimeTicks
		ACCESS          read-only
		STATUS          mandatory
		DESCRIPTION     "0003.0003.0006 This attribute defines the timestamp of the most recent 
                      Fan health status change." 
			::= { drsStatusChangeGroup 6 }

	drsBladeChangeTime  OBJECT-TYPE
		SYNTAX          TimeTicks
		ACCESS          read-only
		STATUS          mandatory
		DESCRIPTION     "0003.0003.0007 This attribute defines the timestamp of the most recent 
                      Blade health status change." 
			::= { drsStatusChangeGroup 7 }

	drsTempChangeTime OBJECT-TYPE
		SYNTAX          TimeTicks
		ACCESS          read-only
		STATUS          mandatory
		DESCRIPTION     "0003.0003.0008 This attribute defines the timestamp of the most recent 
                      Temp Sensor health status change." 
			::= { drsStatusChangeGroup 8 }

	drsCMCChangeTime OBJECT-TYPE
		SYNTAX          TimeTicks
		ACCESS          read-only
		STATUS          mandatory
		DESCRIPTION     "0003.0003.0009 This attribute defines the timestamp of the most recent 
                      CMC health status change." 
			::= { drsStatusChangeGroup 9 }

	-------------------------------------------------------------------------------
	-- group: chassis power
	-------------------------------------------------------------------------------

	drsCMCPowerTable OBJECT-TYPE
		SYNTAX			SEQUENCE OF DrsCMCPowerTableEntry
		ACCESS			not-accessible
		STATUS			mandatory
		DESCRIPTION		"0004.0001 This object defines the CMC power table."
			::= { drsChassisPowerGroup 1 }

	drsCMCPowerTableEntry OBJECT-TYPE
		SYNTAX			DrsCMCPowerTableEntry
		ACCESS      	not-accessible
		STATUS      	mandatory
		DESCRIPTION 	"0004.0001.0001 This object defines the CMC power table entry."
		INDEX       	{ drsChassisIndex }
			::= { drsCMCPowerTable 1 }

	drsCMCPSUTable OBJECT-TYPE
		SYNTAX			SEQUENCE OF DrsCMCPSUTableEntry
		ACCESS			not-accessible
		STATUS			mandatory
		DESCRIPTION		"0004.0002 This object defines the CMC PSU table."
			::= { drsChassisPowerGroup 2 }

	drsCMCPSUTableEntry OBJECT-TYPE
		SYNTAX			DrsCMCPSUTableEntry
		ACCESS      	not-accessible
		STATUS      	mandatory
		DESCRIPTION 	"0004.0002.0001 This object defines the CMC PSU table entry."
		INDEX       	{ drsPSUChassisIndex, drsPSUIndex }
			::= { drsCMCPSUTable 1 }

	-------------------------------------------------------------------------------
	-- table: CMC power information
	-------------------------------------------------------------------------------

	drsChassisIndex OBJECT-TYPE
		SYNTAX			DellCMCPowerIndexRange
		ACCESS			read-only
		STATUS			mandatory
		DESCRIPTION		"0004.0001.0001.0001 This attribute defines the index
							(one-based) of the associated chassis."
			::= { drsCMCPowerTableEntry 1 }

	drsPotentialPower OBJECT-TYPE
		SYNTAX			DellPowerReading
		ACCESS			read-only
		STATUS			mandatory
		DESCRIPTION		"0004.0001.0001.0002 This attribute defines the power (in Watts) required by
							the chassis infrastructure, plus the sum of the maximum power requirements
							for all currently powered-on servers."
			::= { drsCMCPowerTableEntry 2 }

	drsIdlePower OBJECT-TYPE
		SYNTAX			DellPowerReading
		ACCESS			read-only
		STATUS			mandatory
		DESCRIPTION		"0004.0001.0001.0003 This attribute defines the power (in Watts) required by 
							the chassis	infrastructure, plus the sum of the minimum power requirements
							for all currently powered-on servers."
			::= { drsCMCPowerTableEntry 3 }

	drsMaxPowerSpecification OBJECT-TYPE
		SYNTAX			DellPowerReading
		ACCESS			read-only
		STATUS			mandatory
		DESCRIPTION		"0004.0001.0001.0004 This attribute defines the power limit (in Watts) 
							at which server throttling will take place."
			::= { drsCMCPowerTableEntry 4 }


	drsPowerSurplus OBJECT-TYPE
		SYNTAX			DellPowerReading
		ACCESS			read-only
		STATUS			mandatory
		DESCRIPTION		"0004.0001.0001.0005 This attribute defines the power surplus (in Watts)
							remaining above the drsPotentialPower reading." 
			::= { drsCMCPowerTableEntry 5 }

	drsKWhCumulative OBJECT-TYPE
		SYNTAX			DellPowerReading
		ACCESS			read-only
		STATUS			mandatory
		DESCRIPTION		"0004.0001.0001.0006 This attribute defines the cumulative chassis power
							usage (in KWh) since last reset." 
			::= { drsCMCPowerTableEntry 6 }

	drsKWhCumulativeTime OBJECT-TYPE
		SYNTAX			DellTimestamp
		ACCESS			read-only
		STATUS			mandatory
		DESCRIPTION		"0004.0001.0001.0007 This attribute defines the timestamp of the most recent
							chassis power accumulator reset." 
			::= { drsCMCPowerTableEntry 7 }

	drsWattsPeakUsage OBJECT-TYPE
		SYNTAX			DellPowerReading
		ACCESS			read-only
		STATUS			mandatory
		DESCRIPTION		"0004.0001.0001.0008 This attribute defines the chassis peak power
							usage (in Watts) since last reset." 
			::= { drsCMCPowerTableEntry 8 }

	drsWattsPeakTime OBJECT-TYPE
		SYNTAX			DellTimestamp
		ACCESS			read-only
		STATUS			mandatory
		DESCRIPTION		"0004.0001.0001.0009 This attribute defines the timestamp of the most recent
							chassis peak power usage." 
			::= { drsCMCPowerTableEntry 9 }

	drsWattsMinUsage OBJECT-TYPE
		SYNTAX			DellPowerReading
		ACCESS			read-only
		STATUS			mandatory
		DESCRIPTION		"0004.0001.0001.0010 This attribute defines the chassis mimimum power
							usage (in Watts) since last reset." 
			::= { drsCMCPowerTableEntry 10 }

	drsWattsMinTime OBJECT-TYPE
		SYNTAX			DellTimestamp
		ACCESS			read-only
		STATUS			mandatory
		DESCRIPTION		"0004.0001.0001.0011 This attribute defines the timestamp of the most recent
							chassis minimum power usage." 
			::= { drsCMCPowerTableEntry 11 }

	drsWattsResetTime OBJECT-TYPE
		SYNTAX			DellTimestamp
		ACCESS			read-only
		STATUS			mandatory
		DESCRIPTION		"0004.0001.0001.0012 This attribute defines the timestamp of the most recent
							reset of the chassis min/peak Watts readings." 
			::= { drsCMCPowerTableEntry 12 }

	drsWattsReading OBJECT-TYPE
		SYNTAX			DellPowerReading
		ACCESS			read-only
		STATUS			mandatory
		DESCRIPTION		"0004.0001.0001.0013 This attribute defines the instantaneous chassis power
							usage (in Watts)." 
			::= { drsCMCPowerTableEntry 13 }

	drsAmpsReading OBJECT-TYPE
		SYNTAX			DellPowerReading
		ACCESS			read-only
		STATUS			mandatory
		DESCRIPTION		"0004.0001.0001.0014 This attribute defines the instantaneous chassis current
							usage (in Watts)." 
			::= { drsCMCPowerTableEntry 14 }

	-------------------------------------------------------------------------------
	-- table: CMC PSU info
	-------------------------------------------------------------------------------

	drsPSUChassisIndex OBJECT-TYPE
		SYNTAX			DellCMCPowerIndexRange
		ACCESS			read-only
		STATUS			mandatory
		DESCRIPTION		"0004.0002.0001.0001 This attribute defines the index
							(one-based) of the associated chassis."
			::= { drsCMCPSUTableEntry 1 }

	drsPSUIndex OBJECT-TYPE
		SYNTAX			DellCMCPSUIndexRange
		ACCESS			read-only
		STATUS			mandatory
		DESCRIPTION		"0004.0002.0001.0002 This attribute defines the index
							(one-based) of the associated CMC PSU."
			::= { drsCMCPSUTableEntry 2 }

	drsPSULocation OBJECT-TYPE
		SYNTAX			DellString
		ACCESS			read-only
		STATUS			mandatory
		DESCRIPTION		"0004.0002.0001.0003 This attribute defines the location
							of the CMC PSU."
			::= { drsCMCPSUTableEntry 3 }

	drsPSUMonitoringCapable OBJECT-TYPE
		SYNTAX			DellCMCPSUCapable
		ACCESS			read-only
		STATUS			mandatory
		DESCRIPTION		"0004.0002.0001.0004 This attribute defines the PSU Monitoring
							capabilities, or the absence of a PSU in this location."
			::= { drsCMCPSUTableEntry 4 }

	drsPSUVoltsReading OBJECT-TYPE
		SYNTAX			DellPowerReading
		ACCESS			read-only
		STATUS			mandatory
		DESCRIPTION		"0004.0002.0001.0005 This attribute defines the instantaneous
							PSU Voltage reading."
			::= { drsCMCPSUTableEntry 5 }

	drsPSUAmpsReading OBJECT-TYPE
		SYNTAX			DellPowerReading
		ACCESS			read-only
		STATUS			mandatory
		DESCRIPTION		"0004.0002.0001.0006 This attribute defines the instantaneous
							PSU Current reading."
			::= { drsCMCPSUTableEntry 6 }

	drsPSUWattsReading OBJECT-TYPE
		SYNTAX			DellPowerReading
		ACCESS			read-only
		STATUS			mandatory
		DESCRIPTION		"0004.0002.0001.0007 This attribute defines the instantaneous
							PSU Wattage reading."
			::= { drsCMCPSUTableEntry 7 }

	-------------------------------------------------------------------------------
	-- group: chassis servers
	-------------------------------------------------------------------------------

	drsCMCServerTable OBJECT-TYPE
		SYNTAX			SEQUENCE OF DrsCMCServerTableEntry
		ACCESS			not-accessible
		STATUS			mandatory
		DESCRIPTION		"0005.0001 This object defines the CMC server table."
			::= { drsChassisServerGroup 1 }

	drsCMCServerTableEntry OBJECT-TYPE
		SYNTAX			DrsCMCServerTableEntry
		ACCESS      	not-accessible
		STATUS      	mandatory
		DESCRIPTION 	"0005.0001.0001 This object defines the CMC server table entry."
		INDEX       	{ drsServerIndex }
			::= { drsCMCServerTable 1 }

	-------------------------------------------------------------------------------
	-- table: CMC Server info
	-------------------------------------------------------------------------------

	drsServerIndex OBJECT-TYPE
		SYNTAX			DellCMCServerIndexRange
		ACCESS			read-only
		STATUS			mandatory
		DESCRIPTION		"0005.0001.0001.0001 This attribute defines the index
							(one-based) of the associated CMC server."
			::= { drsCMCServerTableEntry 1 }

	drsServerMonitoringCapable OBJECT-TYPE
		SYNTAX			DellCMCServerCapable
		ACCESS			read-only
		STATUS			mandatory
		DESCRIPTION		"0005.0001.0001.0002 This attribute defines the server monitoring
							capabilities, or the absence of a server in this location."
			::= { drsCMCServerTableEntry 2 }

	drsServerServiceTag OBJECT-TYPE
		SYNTAX			DellString
		ACCESS			read-only
		STATUS			mandatory
		DESCRIPTION		"0005.0001.0001.0003 This attribute defines the Service Tag
							of the CMC server."
			::= { drsCMCServerTableEntry 3 }

	drsServerSlotName OBJECT-TYPE
		SYNTAX			DellString
		ACCESS			read-only
		STATUS			mandatory
		DESCRIPTION		"0005.0001.0001.0004 This attribute defines the Slot Name
							of the CMC server."
			::= { drsCMCServerTableEntry 4 }

	drsServerSlotNumber OBJECT-TYPE
		SYNTAX			DellString
		ACCESS			read-only
		STATUS			mandatory
		DESCRIPTION		"0005.0001.0001.0005 This attribute defines the Chassis
							Slot Number of the CMC server."
			::= { drsCMCServerTableEntry 5 }

	drsServerNodeID OBJECT-TYPE
		SYNTAX			DellString
		ACCESS			read-only
		STATUS			mandatory
		DESCRIPTION		"0005.0001.0001.0006 This attribute defines the Node ID
							of the CMC server.  The Node ID provides a unique identifier
							for the server."
			::= { drsCMCServerTableEntry 6 }

	drsServerModel OBJECT-TYPE
		SYNTAX			DellString
		ACCESS			read-only
		STATUS			mandatory
		DESCRIPTION		"0005.0001.0001.0007 This attribute defines the Model
							of the CMC server."
			::= { drsCMCServerTableEntry 7 }

	drsServerAssetTag OBJECT-TYPE
		SYNTAX			DellString
		ACCESS			read-only
		STATUS			mandatory
		DESCRIPTION		"0005.0001.0001.0008 This attribute defines the Asset Tag
							of the CMC server."
			::= { drsCMCServerTableEntry 8 }

	drsServerNumStorageControllers OBJECT-TYPE
		SYNTAX			INTEGER
		ACCESS			read-only
		STATUS			mandatory
		DESCRIPTION		"0005.0001.0001.0009 This attribute defines the number of
							storage controllers on the storage sled.  The value
							will be zero if this is not a storage sled."
			::= { drsCMCServerTableEntry 9 }

	drsServerStorageMode OBJECT-TYPE
		SYNTAX			DellCMCServerStorageMode
		ACCESS			read-only
		STATUS			mandatory
		DESCRIPTION		"0005.0001.0001.0010 This attribute defines the Storage
							Mode of the storage sled."
			::= { drsCMCServerTableEntry 10 }

	drsServerIntrusionState OBJECT-TYPE
		SYNTAX			DellCMCServerIntrusionState
		ACCESS			read-only
		STATUS			mandatory
		DESCRIPTION		"0005.0001.0001.0011 This attribute defines the Intrusion
							State of the CMC server if supported by the server."
			::= { drsCMCServerTableEntry 11 }

	drsServerAssignedServerSlots OBJECT-TYPE
		SYNTAX			DellString
		ACCESS			read-only
		STATUS			mandatory
		DESCRIPTION		"0005.0001.0001.0012 This attribute defines the the server
							slots to which a storage sled is assigned.  If this is
							a storage sled that is assigned to one more or more
							server slots, the value will be a comma-separated list
							of one or more server slot names.  If the storage sled
							is not assigned to a server slot, the value will be an
							empty string.  If this is not a storage sled, the value
							will be N/A."
			::= { drsCMCServerTableEntry 12 }

-------------------------------------------------------------------------------
-- Storage Details Group
--
-- OID Format: 1.3.6.1.4.1.674.10892.5.5
-------------------------------------------------------------------------------


-------------------------------------------------------------------------------
-- Battery Table
--
-- OID Format:.1.3.6.1.4.1.674.10892.2.6.1.20.130.15.1.<a>.<i1>
-------------------------------------------------------------------------------

BatteryTableEntry                               ::=SEQUENCE { 
    batteryNumber                               INTEGER,
    batteryState                                INTEGER,
    batteryComponentStatus                      ObjectStatusEnum,
    batteryPredictedCapacity                    INTEGER,
    batteryFQDD                                 DisplayString,
    batteryDisplayName                          DisplayString
}

batteryTable OBJECT-TYPE
    SYNTAX         SEQUENCE OF BatteryTableEntry
    ACCESS         not-accessible
    STATUS         mandatory
    DESCRIPTION
        "A table of managed batteries. The number of 
        entries is related to number of Batteries
        discovered in the system.  The maximum number of entries 
        is implementation dependent.
        Note: The properties in this table may not be applicable to all 
        entries.
        "
    ::= { physicalDevices 15 }

batteryTableEntry OBJECT-TYPE
    SYNTAX         BatteryTableEntry
    ACCESS         not-accessible
    STATUS         mandatory
    DESCRIPTION
        "An entry in the battery table. A row in this table cannot be
        created or deleted by SNMP operations on columns of the table.
        "
        INDEX { batteryNumber }
    ::= { batteryTable 1 }

batteryNumber OBJECT-TYPE
    SYNTAX         INTEGER (1..255)
    ACCESS         read-only
    STATUS         mandatory
    DESCRIPTION
        "Instance number of this battery entry.
        "
    ::= { batteryTableEntry 1 }

batteryState OBJECT-TYPE
    SYNTAX         INTEGER
		   {
		   unknown(1),
		   ready(2),
		   failed(3),
		   degraded(4),
		   missing(5),
		   charging(6),
		   belowThreshold(7)
		   }
    ACCESS         read-only
    STATUS         mandatory
    DESCRIPTION
        "Current state of battery.
        Possible values:
        1: The current state could not be determined.
        2: The battery is operating normally.
        3: The battery has failed and needs to be replaced.
        4: The battery temperature is high or charge level is depleting.
        5: The battery is missing or not detected. 
        6: The battery is undergoing the re-charge phase.
        7: The battery voltage or charge level is below the threshold.
        "
    ::= { batteryTableEntry 4 }

batteryComponentStatus OBJECT-TYPE
    SYNTAX         ObjectStatusEnum
    ACCESS         read-only
    STATUS         mandatory
    DESCRIPTION
        "The status of the battery itself without the 
        propagation of any contained component status.
        Possible values:
        1: Other
        2: Unknown
        3: OK 
        4: Non-critical 
        5: Critical
        6: Non-recoverable"
    ::= { batteryTableEntry 6 }

batteryPredictedCapacity OBJECT-TYPE
    SYNTAX          INTEGER
                    {
                    unknown(1),
                    failed(2),
                    ready(3)
                    }
    ACCESS          read-only
    STATUS          obsolete
    DESCRIPTION
        "This entry is obsolete. Use the batteryComponentStatus or 
        batteryState instead.
        "
    ::= { batteryTableEntry 10 }

batteryFQDD OBJECT-TYPE
    SYNTAX         DisplayString
    ACCESS         read-only
    STATUS         mandatory
    DESCRIPTION
        "The battery's Fully Qualified Device Descriptor (FQDD) as 
        represented in Storage Management.
        "
    ::= { batteryTableEntry 20 }

batteryDisplayName OBJECT-TYPE
    SYNTAX         DisplayString
    ACCESS         read-only
    STATUS         mandatory
    DESCRIPTION
        "The battery's friendly FQDD as represented in Storage Management."
    ::= { batteryTableEntry 21 }




-------------------------------------------------------------------------------
-- Controller Table
--
-- OID Format:.1.3.6.1.4.1.674.10892.2.6.1.20.130.1.1.<a>.<i1>
-------------------------------------------------------------------------------

ControllerTableEntry                            ::=SEQUENCE { 
    controllerNumber                            INTEGER,
    controllerName                              DisplayString,
    controllerRebuildRate                       INTEGER,
    controllerFWVersion                         DisplayString,
    controllerCacheSizeInMB                     INTEGER,
    controllerRollUpStatus                      ObjectStatusEnum,
    controllerComponentStatus                   ObjectStatusEnum,
    controllerDriverVersion                     DisplayString,
    controllerPCISlot                           DisplayString,
    controllerReconstructRate                   INTEGER,
    controllerPatrolReadRate                    INTEGER,
    controllerBGIRate                           INTEGER,
    controllerCheckConsistencyRate              INTEGER,
    controllerPatrolReadMode                    INTEGER,
    controllerPatrolReadState                   INTEGER,
    controllerPersistentHotSpare                BooleanType,
    controllerSpinDownUnconfiguredDrives        BooleanType,
    controllerSpinDownHotSpareDrives            BooleanType,
    controllerSpinDownTimeInterval              INTEGER,
    controllerPreservedCache                    BooleanType,
    controllerCheckConsistencyMode              INTEGER,
    controllerCopyBackMode                      INTEGER,
    controllerSecurityStatus                    INTEGER,
    controllerEncryptionKeyPresent              BooleanType,
    controllerEncryptionCapability              INTEGER,
    controllerLoadBalanceSetting                INTEGER,    
    controllerMaxCapSpeed                       INTEGER,
    controllerSASAddress                        DisplayString,
    controllerFQDD                              FQDDString,
    controllerDisplayName                       DisplayString,
    controllerT10PICapability                   INTEGER,
    controllerRAID10UnevenSpansSupported        BooleanType,
    controllerEnhancedAutoImportForeignConfigMode INTEGER,  
    controllerBootModeSupported                 BooleanType,
    controllerBootMode                          INTEGER,
    controllerHighAvailabilityMode              INTEGER,
    controllerPeerController                    FQDDString
}

controllerTable OBJECT-TYPE
    SYNTAX         SEQUENCE OF ControllerTableEntry
    ACCESS         not-accessible
    STATUS         mandatory
    DESCRIPTION
        "A table of managed RAID controllers. The number of entries
        is related to number of RAID controllers discovered in the
        system. The maximum number of entries is implementation dependent.
        Note: The properties in this table may not be applicable to all 
        entries.
        "
    ::= { physicalDevices 1 }

controllerTableEntry OBJECT-TYPE
    SYNTAX         ControllerTableEntry
    ACCESS         not-accessible
    STATUS         mandatory
    DESCRIPTION
        "An entry in the table of RAID controllers. A row in this table 
        cannot be created or deleted by SNMP operations on columns of 
        the table."
    INDEX         { controllerNumber }
    ::= { controllerTable 1 }

controllerNumber OBJECT-TYPE
    SYNTAX         INTEGER (1..255)
    ACCESS         read-only
    STATUS         mandatory
    DESCRIPTION
        "Instance number of this controller entry."
    ::= { controllerTableEntry 1 }


controllerName OBJECT-TYPE
    SYNTAX         DisplayString
    ACCESS         read-only
    STATUS         mandatory
    DESCRIPTION
        "The controller's name as represented in Storage Management.
        "
    ::= { controllerTableEntry 2 }

controllerRebuildRate OBJECT-TYPE
    SYNTAX         INTEGER (0..100)
    ACCESS         read-only
    STATUS         mandatory
    DESCRIPTION
        "The rebuild rate is the percentage of the controller's 
        resources dedicated to rebuilding a failed disk when a rebuild 
        is necessary.
        "
    ::= { controllerTableEntry 7 }

controllerFWVersion OBJECT-TYPE
    SYNTAX         DisplayString
    ACCESS         read-only
    STATUS         mandatory
    DESCRIPTION
        "The controller's current firmware version.
        "
    ::= { controllerTableEntry 8 }

controllerCacheSizeInMB OBJECT-TYPE
    SYNTAX         INTEGER
    ACCESS         read-only
    STATUS         mandatory
    DESCRIPTION
        "The controller's current amount of cache memory in megabytes.  
        "
    ::= { controllerTableEntry 9 }

controllerRollUpStatus OBJECT-TYPE
    SYNTAX         ObjectStatusEnum
    ACCESS         read-only
    STATUS         mandatory
    DESCRIPTION
        "Severity of the controller state.  
        This is the combined status of the controller and its components.
        Possible values:
        1: Other.
        2: Unknown.
        3: OK 
        4: Non-critical 
        5: Critical.
        6: Non-recoverable.
        "
    ::= { controllerTableEntry 37 }

controllerComponentStatus OBJECT-TYPE
    SYNTAX          ObjectStatusEnum
    ACCESS          read-only
    STATUS          mandatory
    DESCRIPTION
        "The status of the controller itself without the 
        propagation of any contained component status.
        Possible values:
        1: Other
        2: Unknown
        3: OK 
        4: Non-critical 
        5: Critical
        6: Non-recoverable"
    ::= { controllerTableEntry 38 }

controllerDriverVersion OBJECT-TYPE
    SYNTAX          DisplayString
    ACCESS          read-only
    STATUS          mandatory
    DESCRIPTION
        "Currently installed driver version for this controller on the host.
        "
    ::= { controllerTableEntry 41 }

controllerPCISlot OBJECT-TYPE
    SYNTAX         DisplayString
    ACCESS         read-only
    STATUS         mandatory
    DESCRIPTION
        "The PCI slot on the server where the controller is seated. This 
        data is not reported for embedded or integrated controllers, 
        "
    ::= { controllerTableEntry 42 }

controllerReconstructRate OBJECT-TYPE
    SYNTAX         INTEGER (0..100)
    ACCESS         read-only
    STATUS         mandatory
    DESCRIPTION
        "The reconstruct rate is the percentage of the controller's resources 
        dedicated to reconstructing a disk group after adding a physical disk 
        or changing the RAID level of a virtual disk residing on the disk 
        group.
        "
    ::= { controllerTableEntry 48 }

controllerPatrolReadRate OBJECT-TYPE
    SYNTAX         INTEGER (0..100)
    ACCESS         read-only
    STATUS         mandatory
    DESCRIPTION
        "The patrol read rate is the percentage of the controller's 
        resources dedicated to perform a patrol read on disks participating
        in a virtual disk or hot spares.
        "
    ::= { controllerTableEntry 49 }

controllerBGIRate OBJECT-TYPE
    SYNTAX         INTEGER (0..100)
    ACCESS         read-only
    STATUS         mandatory
    DESCRIPTION
        "The background initialization (BGI) rate is the percentage of the 
        controller's resources dedicated to performing the background 
        initialization of a redundant virtual disk after it is created.
        "
    ::= { controllerTableEntry 50 }

controllerCheckConsistencyRate OBJECT-TYPE
    SYNTAX         INTEGER (0..100)
    ACCESS         read-only
    STATUS         mandatory
    DESCRIPTION
        "The check consistency rate is the percentage of the 
        controller's resources dedicated to performing a check consistency 
        on a redundant virtual disk.
        "
    ::= { controllerTableEntry 51 }

controllerPatrolReadMode OBJECT-TYPE
    SYNTAX         INTEGER
           {
           other(1),
           notSupported(2),
           disabled(3),
           auto(4),
           manual(5)
           }
    ACCESS         read-only
    STATUS         mandatory
    DESCRIPTION
        "Identifies the patrol read mode setting for the controller.
        Possible values:
        1: Not one of the following or could not be determined.
        2: Not Supported on this controller. 
        3: Disabled.
        4: Automatic.
        5: Manual.
        "
    ::= { controllerTableEntry 52 }
    
controllerPatrolReadState OBJECT-TYPE
    SYNTAX          INTEGER
                    {
                    other(1),
                    stopped(2),
                    active(3)
                    }
    ACCESS          read-only
    STATUS          mandatory
    DESCRIPTION
        "This property displays the current state of the patrol read process.
         Possible values:
        1: Not one of the following or could not be determined.
        2: Patrol read is not running.
        3: Patrol read is running.
        "
    ::= { controllerTableEntry 53 }

controllerPersistentHotSpare OBJECT-TYPE
    SYNTAX          BooleanType
    ACCESS          read-only
    STATUS          mandatory
    DESCRIPTION
        "Indicates whether hot spare drives would be restored on insertion 
        into the same slot.
        "
    ::= { controllerTableEntry 59 }

controllerSpinDownUnconfiguredDrives OBJECT-TYPE
    SYNTAX          BooleanType
    ACCESS          read-only
    STATUS          mandatory
    DESCRIPTION
        "Indicates whether un-configured drives would be put in power
        save mode by the controller.
        "
    ::= { controllerTableEntry 60 }

controllerSpinDownHotSpareDrives OBJECT-TYPE
    SYNTAX          BooleanType
    ACCESS          read-only
    STATUS          mandatory
    DESCRIPTION
        "Indicates whether hot spare drives would be put in power
        save mode by the controller.
        "
    ::= { controllerTableEntry 61 }

controllerSpinDownTimeInterval OBJECT-TYPE
    SYNTAX          INTEGER (30..1440)
    ACCESS          read-only
    STATUS          mandatory
    DESCRIPTION
        "The duration in minutes after which, the unconfigured or hot 
        spare drives will be spun down to power save mode.
        "
    ::= { controllerTableEntry 62 }

controllerPreservedCache OBJECT-TYPE
    SYNTAX          BooleanType
    ACCESS          read-only
    STATUS          mandatory
    DESCRIPTION
        "Indicates whether preserved cache or pinned cache is 
        present on the controller.
        "
    ::= { controllerTableEntry 69 }

controllerCheckConsistencyMode OBJECT-TYPE
    SYNTAX          INTEGER
                    {
                    other(1),
                    unsupported(2),
                    normal(3),
                    stopOnError(4)
                    }
    ACCESS          read-only
    STATUS          mandatory
    DESCRIPTION
        "The current check consistency mode setting 
        for the controller.
        Possible values:
        1: Not one of the following.
        2: Not supported on this controller.
        3: Normal check consistency operation.
        4: Check consistency operation will stop on encountering 
        an error.
        "
    ::= { controllerTableEntry 70 }

controllerCopyBackMode OBJECT-TYPE
    SYNTAX          INTEGER
                    {
                    other(1),
                    unsupported(2),
                    on(3),
                    onWithSmart(4),
                    off(5)
                    }
    ACCESS          read-only
    STATUS          mandatory
    DESCRIPTION
        "The current copy back mode setting 
        for the controller.
        Possible values:
        1: Not one of the following.
        2: Not supported on this controller.
        3: Disks assigned as spares could revert back to spare status.
        4: Data from physical disk participating in a 
        virtual disk could be automatically copied to the assigned 
        hot spare in case former has a predictive failure event. 
        5: Copyback mode is disabled. 
        "
    ::= { controllerTableEntry 71 }

controllerSecurityStatus OBJECT-TYPE
    SYNTAX          INTEGER
                    {
                    unknown(1),
                    none(2),
                    lkm(3)
                    }
    ACCESS          read-only
    STATUS          mandatory
    DESCRIPTION
        "The controller's current security/encryption status..
        Possible values:
        1: The current status could not be determined.
        2: Controller is not operating in an encryption mode.
        3: Controller is operating in the Local Key Management
        (LKM) encryption mode.
        "
    ::= { controllerTableEntry 72 }

controllerEncryptionKeyPresent OBJECT-TYPE
    SYNTAX          BooleanType
    ACCESS          read-only
    STATUS          mandatory
    DESCRIPTION
        "Indicates whether encryption key is assigned for the controller.
        "
    ::= { controllerTableEntry 73 }

controllerEncryptionCapability OBJECT-TYPE
    SYNTAX          INTEGER
                    {
                    other(1),
                    none(2),
                    lkm(3)
                    }
    ACCESS          read-only
    STATUS          mandatory
    DESCRIPTION
    "The type of encryption supported by the controller.
    Possible values:
    1: Not one of the following.
    2: No encryption supported, 
    3: Local Key Management,
    "
    ::= { controllerTableEntry 74 }

controllerLoadBalanceSetting OBJECT-TYPE
    SYNTAX          INTEGER
                    {
                    other(1),
                    unsupported(2),
                    auto(3),
                    none(4)
                    }
    ACCESS          read-only
    STATUS          mandatory
    DESCRIPTION
        "The ability of the controller to automatically use both 
        controller ports (or connectors) connected to the same enclosure in 
        order to route I/O requests.
        Possible values:
        1: Not one of the following.
        2: Not supported.
        3: Automatic load balancing is active.
        4: Load balancing is inactive.
        "
    ::= { controllerTableEntry 75 }

controllerMaxCapSpeed OBJECT-TYPE
    SYNTAX          INTEGER
                    {
                    unknown(1),
                    oneDotFiveGbps(2),
                    threeGbps(3),
                    sixGbps(4),
                    twelveGbps(5)
                    }
    ACCESS          read-only
    STATUS          mandatory
    DESCRIPTION
        "The maximum speed of the controller.in 
        Gigbits per second (Gbps).
        Possible values:
        1: The speed could not be determined.
        2. 1.5 Gbps
        3: 3.0 Gbps
        4: 6.0 Gbps
        5: 12.0 Gbps
        "
    ::= { controllerTableEntry 76 }

controllerSASAddress OBJECT-TYPE
    SYNTAX         DisplayString
    ACCESS         read-only
    STATUS         mandatory
    DESCRIPTION
        "The SAS address of the controller.
        "
    ::= { controllerTableEntry 77 }

controllerFQDD OBJECT-TYPE
    SYNTAX         FQDDString
    ACCESS         read-only
    STATUS         mandatory
    DESCRIPTION
        "The controller's Fully Qualified Device Descriptor (FQDD) as 
        represented in Storage Management.
        "
    ::= { controllerTableEntry 78 }

controllerDisplayName OBJECT-TYPE
    SYNTAX         DisplayString
    ACCESS         read-only
    STATUS         mandatory
    DESCRIPTION
        "The controller's friendly FQDD as represented in Storage 
    Management."
    ::= { controllerTableEntry 79 }

controllerT10PICapability OBJECT-TYPE
    SYNTAX          INTEGER
                    {
                    other(1),
                    capable(2),
                    notCapable(3)
                    }
    ACCESS          read-only
    STATUS          mandatory
    DESCRIPTION
        "Indicates whether the controller supports the T10 PI (Protection 
        Information). These protection fields are known as DIF
        (Data Integrity Fields).
        Possible values:
        1: Not one of the following.
        2: Capable of supporting T10 PI.
        3: Not capable of supporting T10 PI.
        "
    ::= { controllerTableEntry 80 }

controllerRAID10UnevenSpansSupported OBJECT-TYPE
    SYNTAX          BooleanType
    ACCESS          read-only
    STATUS          mandatory
    DESCRIPTION
        "Indicates whether uneven spans for RAID 10 virtual disk 
        is supported on the controller.
        "
    ::= { controllerTableEntry 81 }

controllerEnhancedAutoImportForeignConfigMode OBJECT-TYPE
    SYNTAX          INTEGER
                    {
                    other(1),
                    notSupported(2),
                    disabled(3),
                    enabled(4)
                    }
    ACCESS          read-only
    STATUS          mandatory
    DESCRIPTION
        "Indicates the status of enhanced auto-import of foreign 
        configuration property of the controller.
        1: Not one of the following.
        2: Not Supported.
        3: Disabled.
        4: Enabled.
        "
    ::= { controllerTableEntry 82 }

controllerBootModeSupported OBJECT-TYPE
    SYNTAX          BooleanType
    ACCESS          read-only
    STATUS          mandatory
    DESCRIPTION
        "Indicates whether headless boot mode settings are supported 
        on the controller.
        "
    ::= { controllerTableEntry 83 }

controllerBootMode OBJECT-TYPE
    SYNTAX          INTEGER
                    {
                    notApplicable(1),
                    user(2),
                    contOnError(3),
                    headlessContOnError(4),
                    headlessSafe(5)
                    }
    ACCESS          read-only
    STATUS          mandatory
    DESCRIPTION
        "Indicates the boot mode of the controller.
        Possible values:
        1: Not applicable for this controller.
        2: User mode: User interaction required for all boot messages (not 
        applicable for uEFI environments).
        3: Continue Boot On Error. User interaction only required for 
        critical messages.
        4: Headless Mode Continue On Error. User interaction is not required.
        Controller boot may halt on Error.
        5: Headless Safe Mode. Controller shall boot to safe mode on critical
        errors.
        "
    ::= { controllerTableEntry 84 }

controllerHighAvailabilityMode OBJECT-TYPE
    SYNTAX          INTEGER
                    {
                    None (1),
                    FaultTolerantActivePassive (2),
                    FaultTolerantActiveActive (3),
                    Degraded (4)
                    }
    ACCESS          read-only
    STATUS          mandatory
    DESCRIPTION
        "Indicates the fault-tolerant mode of the controller.
        Possible values:
        1: None
        2: Fault Tolerant(Active/Passive)
        3: Fault Tolerant(Active/Active)
        4: Degraded
        "
    ::= { controllerTableEntry 85 }

controllerPeerController OBJECT-TYPE
    SYNTAX         FQDDString
    ACCESS         read-only
    STATUS         mandatory
    DESCRIPTION
        "The peer controller's Fully Qualified Device Descriptor (FQDD) as 
        represented in Storage Management.
        "
    ::= { controllerTableEntry 86 }





-------------------------------------------------------------------------------
-- Physical Disk Table
--
-- OID Format:.1.3.6.1.4.1.674.10892.2.6.1.20.130.4.1.<a>.<i1>
-------------------------------------------------------------------------------

PhysicalDiskTableEntry                          ::=SEQUENCE { 
    physicalDiskNumber                          INTEGER,
    physicalDiskName                            DisplayString,
    physicalDiskManufacturer                    DisplayString,    
    physicalDiskState                           INTEGER,
    physicalDiskProductID                       DisplayString,
    physicalDiskSerialNo                        DisplayString,
    physicalDiskRevision                        DisplayString,
    physicalDiskCapacityInMB                    INTEGER,
    physicalDiskUsedSpaceInMB                   INTEGER,
    physicalDiskFreeSpaceInMB                   INTEGER,
    physicalDiskBusType                         INTEGER,
    physicalDiskSpareState                      INTEGER,
    physicalDiskComponentStatus                 ObjectStatusEnum,    
    physicalDiskPartNumber                      DisplayString,
    physicalDiskSASAddress                      DisplayString,
    physicalDiskNegotiatedSpeed                 INTEGER,
    physicalDiskCapableSpeed                    INTEGER,
    physicalDiskSmartAlertIndication            BooleanType,
    physicalDiskManufactureDay                  DisplayString,
    physicalDiskManufactureWeek                 DisplayString,
    physicalDiskManufactureYear                 DisplayString,
    physicalDiskMediaType                       INTEGER,
    physicalDiskPowerState                      INTEGER,
    physicalDiskRemainingRatedWriteEndurance    INTEGER,
    physicalDiskOperationalState                INTEGER,
    physicalDiskProgress                        INTEGER,
    physicalDiskSecurityStatus                  INTEGER,
    physicalDiskFormFactor                      INTEGER,
    physicalDiskFQDD                            FQDDString,
    physicalDiskDisplayName                     DisplayString,
    physicalDiskT10PICapability                 INTEGER,
    physicalDiskBlockSizeInBytes                INTEGER,
    physicalDiskProtocolVersion                 DisplayString,
    physicalDiskPCIeNegotiatedLinkWidth         INTEGER,
    physicalDiskPCIeCapableLinkWidth            INTEGER,
    physicalDiskCurrentActiveController         FQDDString,
    physicalDiskFailoverController              FQDDString
 }

physicalDiskTable OBJECT-TYPE
    SYNTAX          SEQUENCE OF PhysicalDiskTableEntry
    ACCESS          not-accessible
    STATUS          mandatory
    DESCRIPTION
        "A table of managed physical disks. The number of entries is 
        related to number of physical Disks discovered in the system.
        The maximum number of entries is implementation dependent.
        Note: The properties in this table may not be applicable to 
        all entries.
        "
    ::= { physicalDevices 4 }

physicalDiskTableEntry OBJECT-TYPE
    SYNTAX          PhysicalDiskTableEntry
    ACCESS          not-accessible
    STATUS          mandatory
    DESCRIPTION
        "An entry in the physical Disk table. A row in this table cannot be
        created or deleted by SNMP operations on columns of the table.
        "
    INDEX         { physicalDiskNumber }
    ::= { physicalDiskTable 1 }

physicalDiskNumber OBJECT-TYPE
    SYNTAX          INTEGER (1..1000000000)
    ACCESS          read-only
    STATUS          mandatory
    DESCRIPTION
        "Instance number of this physical disk entry.
        "
    ::= { physicalDiskTableEntry 1 }

physicalDiskName OBJECT-TYPE
    SYNTAX          DisplayString
    ACCESS          read-only
    STATUS          mandatory
    DESCRIPTION
        "The physical disk's name as represented in Storage Management.
        "
    ::= { physicalDiskTableEntry 2 }

physicalDiskManufacturer OBJECT-TYPE    
    SYNTAX          DisplayString
    ACCESS          read-only
    STATUS          mandatory
    DESCRIPTION
        "The name of the physical disk's manufacturer.
        "
    ::= { physicalDiskTableEntry 3 }

physicalDiskState OBJECT-TYPE
    SYNTAX          INTEGER
                    {
                    unknown(1),
                    ready(2),
                    online(3),
                    foreign(4),
                    offline(5),
                    blocked(6),
                    failed(7),
                    nonraid(8),
                    removed(9),
                    readonly(10)
                    }
    ACCESS          read-only
    STATUS          mandatory
    DESCRIPTION
        "The current state of this physical disk.
        Possible states:
        1: The current state could not be determined.
        2: The physical disk is available for use, but no RAID configuration 
        has been assigned. 
        3: A RAID configuration has been assigned to the physical disk.
        4: The physical disk has been moved from another
        controller and contains all or some portion of a virtual disk.
        5: The physical disk is not available to the RAID
        controller. 
        6: The physical disk is currently blocked by
        controller.
        7: The physical disk is not operational.
        8: The physical disk is not a RAID capable disk 
        9: The physical disk has been removed.
        10:The physical disk media has been placed in read only mode.
        "
    ::= { physicalDiskTableEntry 4 }

physicalDiskProductID OBJECT-TYPE
    SYNTAX          DisplayString
    ACCESS          read-only
    STATUS          mandatory
    DESCRIPTION
        "The model number of the physical disk.
        "
    ::= { physicalDiskTableEntry 6 }

physicalDiskSerialNo OBJECT-TYPE
    SYNTAX          DisplayString
    ACCESS          read-only
    STATUS          mandatory
    DESCRIPTION
        "The physical disk's unique identification number 
        from the manufacturer.
        "
    ::= { physicalDiskTableEntry 7 }

physicalDiskRevision OBJECT-TYPE
    SYNTAX          DisplayString
    ACCESS          read-only
    STATUS          mandatory
    DESCRIPTION
        "The firmware version of the physical disk.
        "
    ::= { physicalDiskTableEntry 8 }

physicalDiskCapacityInMB OBJECT-TYPE
    SYNTAX          INTEGER
    ACCESS          read-only
    STATUS          mandatory
    DESCRIPTION
        "The size of the physical disk in megabytes.
        "        
    ::= { physicalDiskTableEntry 11 }

physicalDiskUsedSpaceInMB OBJECT-TYPE
    SYNTAX          INTEGER
    ACCESS          read-only
    STATUS          mandatory
    DESCRIPTION
        "The amount of used space in megabytes on the physical
        disk. This is not applicable for NVMe devices.
        "
    ::= { physicalDiskTableEntry 17 }

physicalDiskFreeSpaceInMB OBJECT-TYPE
    SYNTAX          INTEGER
    ACCESS          read-only
    STATUS          mandatory
    DESCRIPTION
        "The amount of free space in megabytes on the physical
        disk. This is not applicable for NVMe devices.
        "
    ::= { physicalDiskTableEntry 19 }    

physicalDiskBusType OBJECT-TYPE
    SYNTAX          INTEGER
                    {
                    unknown(1),
                    scsi(2),
                    sas(3),
                    sata(4),
                    fibre(5),
                    pcie(6)
                    }
    ACCESS          read-only
    STATUS          mandatory
    DESCRIPTION
        "The bus type of the physical disk.
        Possible values:
        1: The bus type could not be determined.
        2: Small Computer System Interface (SCSI).
        3: Serial Attached SCSI (SAS).
        4: Serial Advanced Technology Attachment (SATA).
        5: Fibre channel.
        6: PCIe.
        "
    ::= { physicalDiskTableEntry 21 }    

physicalDiskSpareState OBJECT-TYPE
    SYNTAX          INTEGER
                    {
                    notASpare(1),
                    dedicatedHotSpare(2),
                    globalHotSpare(3)
                    }
    ACCESS          read-only
    STATUS          mandatory
    DESCRIPTION
        "The status of the disk as a spare.
        Possible values:
        1: Physical disk is not a spare.
        2: Physical disk is a dedicated hot spare.
        3: Physical disk is a global hot spare.
        "
    ::= { physicalDiskTableEntry 22 }

physicalDiskComponentStatus OBJECT-TYPE
    SYNTAX          ObjectStatusEnum
    ACCESS          read-only
    STATUS          mandatory
    DESCRIPTION
        "The status of the physical disk itself without the 
        propagation of any contained component status.
        Possible values:
        1: Other
        2: Unknown
        3: OK 
        4: Non-critical 
        5: Critical
        6: Non-recoverable
        "
    ::= { physicalDiskTableEntry 24 }

physicalDiskPartNumber OBJECT-TYPE
    SYNTAX          DisplayString
    ACCESS          read-only
    STATUS          mandatory
    DESCRIPTION
        "The part number of the disk.
        "
    ::= { physicalDiskTableEntry 27 }

physicalDiskSASAddress OBJECT-TYPE
    SYNTAX          DisplayString
    ACCESS          read-only
    STATUS          mandatory
    DESCRIPTION
        "The SAS address of the physical disk.
        "
    ::= { physicalDiskTableEntry 28 }

physicalDiskNegotiatedSpeed OBJECT-TYPE
    SYNTAX          INTEGER
                    {
                    unknown(1),
                    oneDotFiveGbps(2),
                    threeGbps(3),
                    sixGbps(4),
                    twelveGbps(5),
                    fiveGTps(6),
                    eightGTps(7)
                    }
    ACCESS          read-only
    STATUS          mandatory
    DESCRIPTION
        "The data transfer speed that the disk negotiated while spinning up 
        in Gigbits per second (Gbps).
        Possible values:
        1: The speed could not be determined.
        2. 1.5 Gbps
        3: 3.0 Gbps
        4: 6.0 Gbps
        5: 12.0 Gbps
        6: 5 GT/s (applicable for NVMe devices).
        7: 8 GT/s (applicable for NVMe devices).
        "
    ::= { physicalDiskTableEntry 29 }

physicalDiskCapableSpeed OBJECT-TYPE
    SYNTAX          INTEGER
                    {
                    unknown(1),
                    oneDotFiveGbps(2),
                    threeGbps(3),
                    sixGbps(4),
                    twelveGbps(5),
                    fiveGTps(6),
                    eightGTps(7)

                    }
    ACCESS          read-only
    STATUS          mandatory
    DESCRIPTION
        "The maximum data transfer speed supported by the disk 
        in Gigbits per second (Gbps).
        Possible values:
        1: The speed could not be determined.
        2. 1.5 Gbps
        3: 3.0 Gbps
        4: 6.0 Gbps
        5: 12.0 Gbps
        6: 5 GT/s (applicable for NVMe devices).
        7: 8 GT/s (applicable for NVMe devices).
        "
    ::= { physicalDiskTableEntry 30 }

physicalDiskSmartAlertIndication OBJECT-TYPE
    SYNTAX          BooleanType
    ACCESS          read-only
    STATUS          mandatory
    DESCRIPTION
        "Indicates whether the physical disk has received a predictive 
        failure alert.
        "
    ::= { physicalDiskTableEntry 31 }

physicalDiskManufactureDay OBJECT-TYPE
    SYNTAX          DisplayString
    ACCESS          read-only
    STATUS          mandatory
    DESCRIPTION
        "The day of the week (1=Sunday thru 7=Saturday) 
        on which the physical disk was manufactured.
        "
    ::= { physicalDiskTableEntry 32 }

physicalDiskManufactureWeek OBJECT-TYPE
    SYNTAX          DisplayString
    ACCESS          read-only
    STATUS          mandatory
    DESCRIPTION
        "The week (1 thru 53) in which the physical disk 
        was manufactured.
        "
    ::= { physicalDiskTableEntry 33 }

physicalDiskManufactureYear OBJECT-TYPE    
    SYNTAX          DisplayString
    ACCESS          read-only
    STATUS          mandatory
    DESCRIPTION
        "The four digit year in which the physical disk was manufactured.
        "
    ::= { physicalDiskTableEntry 34 }

physicalDiskMediaType OBJECT-TYPE
    SYNTAX          INTEGER
                    {
                    unknown(1),
                    hdd(2),
                    ssd(3)
                    }
    ACCESS          read-only
    STATUS          mandatory
    DESCRIPTION
        "The media type of the physical disk.
        Possible Values:
        1: The media type could not be determined.
        2: Hard Disk Drive (HDD).
        3: Solid State Device (SSD).
        "
    ::= { physicalDiskTableEntry 35 }

physicalDiskPowerState OBJECT-TYPE
    SYNTAX          INTEGER
                    {
                    other(1),
                    spunUp(2),
                    spunDown(3),
                    transition(4),
                    on(5)
                    }
    ACCESS          read-only
    STATUS          mandatory
    DESCRIPTION
        "The power state of the physical disk.
        Possible Values:
        1: Not one of the following.
        2: The physical disk is in the spun up state.
        3: The physical disk is in the spun down state.
        4: The physical disk is changing from spun down state
        to spun up state or vice versa.
        5: The Solid State Device (SSD) is powered on.
        "
    ::= { physicalDiskTableEntry 42 }

physicalDiskRemainingRatedWriteEndurance OBJECT-TYPE
    SYNTAX          INTEGER (0..255)
    ACCESS          read-only
    STATUS          mandatory
    DESCRIPTION
        "This property is applicable to SSD media type only. This indicates 
        the wear-out percentage of the SSD. Typically it is a value between 
        0 to 100. However, if the value is not available or not applicable 
        (in the case of HDD media type) the value will be 255.
        "
    ::= { physicalDiskTableEntry 49 }    

physicalDiskOperationalState OBJECT-TYPE
    SYNTAX          INTEGER
                    {
                    notApplicable(1),
                    rebuild(2),
                    clear(3),
                    copyback(4)
                    }
    ACCESS          read-only
    STATUS          mandatory
    DESCRIPTION
        "The state of the physical disk when there are progressive
        operations ongoing.
        Possible values:
        1: There is no active operation running.
        2: Data from a redundant virtual disk is 
        currently being rebuilt onto the physical disk.
        3: Data on the disk is being erased.
        4: Data is being copied from a hot spare disk to 
        the physical disk or vice versa.
         "
    ::= { physicalDiskTableEntry 50 }

physicalDiskProgress OBJECT-TYPE
    SYNTAX          INTEGER (0..100)
    ACCESS          read-only
    STATUS          mandatory
    DESCRIPTION
        "The progress percentage of the operation that is being 
        performed on the physical disk. This is applicable 
        only if there is a progressive operations ongoing
        "
    ::= { physicalDiskTableEntry 51 }

physicalDiskSecurityStatus OBJECT-TYPE
    SYNTAX          INTEGER
                    {
                    supported(1),
                    notSupported(2),
                    secured(3),
                    locked(4),
                    foreign(5)
                    }
    ACCESS          read-only
    STATUS          mandatory
    DESCRIPTION
        "The security/encryption status of the physical disk.
        Possible Values:
        1: The physical disk supports encryption.
        2: The physical disk does not support encryption
        3: The physical disk is encrypted.
        4: The physical disk is locked by a key.
        5: The physical disk is locked by a foreign key.
        "
    ::= { physicalDiskTableEntry 52 }

physicalDiskFormFactor OBJECT-TYPE
    SYNTAX          INTEGER
                    {
                    unknown(1),
                    oneDotEight(2),
                    twoDotFive(3),
                    threeDotFive(4)
                    }
    ACCESS          read-only
    STATUS          mandatory
    DESCRIPTION
        "The form factor of the physical disk.
        Possible values:
        1: The form factor could not be determined.
        2: 1.8 inch.
        3: 2.5 inch.
        4: 3.5 inch.
        "
    ::= { physicalDiskTableEntry 53 }

physicalDiskFQDD OBJECT-TYPE
    SYNTAX          FQDDString
    ACCESS          read-only
    STATUS          mandatory
    DESCRIPTION
        "The physical disk's Fully Qualified Device Descriptor (FQDD) 
        as represented in Storage Management.
        "
    ::= { physicalDiskTableEntry 54 }

physicalDiskDisplayName OBJECT-TYPE
    SYNTAX          DisplayString
    ACCESS          read-only
    STATUS          mandatory
    DESCRIPTION
        "The physical disk's friendly FQDD as represented in Storage 
        Management.
        "
    ::= { physicalDiskTableEntry 55 }

physicalDiskT10PICapability OBJECT-TYPE
    SYNTAX          INTEGER
                    {
                    other(1),
                    capable(2),
                    notCapable(3)
                    }
    ACCESS          read-only
    STATUS          mandatory
    DESCRIPTION
        "Indicates whether the physical disk supports the T10 PI (Protection 
        Information). These protection fields are known as DIF 
        (Data Integrity Fields).
        Possible values:
        1: Not one of the following.
        2: Capable of supporting T10 PI.
        3: Not capable of supporting T10 PI.
        "
    ::= { physicalDiskTableEntry 57 }

physicalDiskBlockSizeInBytes OBJECT-TYPE
    SYNTAX          INTEGER
    ACCESS          read-only
    STATUS          mandatory
    DESCRIPTION
        "The block size (in bytes) of the physical disk. This is not 
        applicable for NVMe devices.
        Possible values:
        1: 512.
        2: 4096
        "
    ::= { physicalDiskTableEntry 58 }
    
physicalDiskProtocolVersion OBJECT-TYPE
    SYNTAX          DisplayString
    ACCESS          read-only
    STATUS          mandatory
    DESCRIPTION
        "Applicable for NVMe devices only. The NVMe protocol version supported 
        by the device.
        "
    ::= { physicalDiskTableEntry 59 }

physicalDiskPCIeNegotiatedLinkWidth OBJECT-TYPE
    SYNTAX          INTEGER
                    {
                    other(1),
                    notApplicable(2),
                    byOne(3),
                    byTwp(4),
                    byFour(5),
                    byEight(6),
                    bySixteen(7),
                    byThirtyTwp(8)
                    }
    ACCESS          read-only
    STATUS          mandatory
    DESCRIPTION
        "Applicable for NVMe devices  only. The PCIe link width negotiated with the host
        during device initialization.
        "
    ::= { physicalDiskTableEntry 60 }

physicalDiskPCIeCapableLinkWidth OBJECT-TYPE
    SYNTAX          INTEGER
                    {
                    other(1),
                    notApplicable(2),
                    byOne(3),
                    byTwp(4),
                    byFour(5),
                    byEight(6),
                    bySixteen(7),
                    byThirtyTwp(8)
                    }
    ACCESS          read-only
    STATUS          mandatory
    DESCRIPTION
        "Applicable for NVMe devices only. The PCIe link widths the device is capable of 
        supporting.
        "
    ::= { physicalDiskTableEntry 61 }

physicalDiskCurrentActiveController  OBJECT-TYPE
    SYNTAX          FQDDString
    ACCESS          read-only
    STATUS          mandatory
    DESCRIPTION
        "Indicates the Fully Qualified Device Descriptor (FQDD) of 
        the current active controller.
        "
    ::= { physicalDiskTableEntry 62 }

physicalDiskFailoverController    OBJECT-TYPE
    SYNTAX          FQDDString
    ACCESS          read-only
    STATUS          mandatory
    DESCRIPTION
        "Indicates the Fully Qualified Device Descriptor (FQDD) of 
        the failover controller.
        "
    ::= { physicalDiskTableEntry 63 }




-------------------------------------------------------------------------------
-- Virtual Disk Table
--
-- OID Format:.1.3.6.1.4.1.674.10892.2.6.1.20.140.1.1.<a>.<i1>
-------------------------------------------------------------------------------
VirtualDiskTableEntry                          ::=SEQUENCE { 
    virtualDiskNumber                           INTEGER,
    virtualDiskName                             DisplayString,
    virtualDiskState                            INTEGER,
    virtualDiskSizeInMB                         INTEGER,
    virtualDiskWritePolicy                      INTEGER,
    virtualDiskReadPolicy                       INTEGER,
    virtualDiskLayout                           INTEGER,
    virtualDiskStripeSize                       INTEGER,
    virtualDiskComponentStatus                  ObjectStatusEnum,        
    virtualDiskBadBlocksDetected                BooleanType,
    virtualDiskSecured                          BooleanType,
    virtualDiskIsCacheCade                      BooleanType,
    virtualDiskDiskCachePolicy                  INTEGER,
    virtualDiskOperationalState                 INTEGER,
    virtualDiskProgress                         INTEGER,
    virtualDiskAvailableProtocols               DisplayString,
    virtualDiskMediaType                        DisplayString,
    virtualDiskRemainingRedundancy              INTEGER,
    virtualDiskFQDD                             FQDDString,
    virtualDiskDisplayName                      DisplayString,
    virtualDiskT10PIStatus                      INTEGER,
    virtualDiskBlockSizeInBytes                 INTEGER,
    virtualDiskAdapter1AccessPolicy             INTEGER,
    virtualDiskAdapter2AccessPolicy             INTEGER,
    virtualDiskAdapter3AccessPolicy             INTEGER,
    virtualDiskAdapter4AccessPolicy             INTEGER,
    virtualDiskCurrentActiveController          FQDDString,
    virtualDiskFailoverController               FQDDString
}

virtualDiskTable OBJECT-TYPE
    SYNTAX          SEQUENCE OF VirtualDiskTableEntry
    ACCESS          not-accessible
    STATUS          mandatory
    DESCRIPTION
        "A table of managed virtual disks. The number of entries is related
        to number of virtual disks discovered in the system. 
        The maximum number of entries is implementation dependent.
        Note: The properties in this table may not be applicable to all
        entries.
        "
    ::= { logicalDevices 1 }

virtualDiskTableEntry OBJECT-TYPE
    SYNTAX          VirtualDiskTableEntry
    ACCESS          not-accessible
    STATUS          mandatory
    DESCRIPTION
        "An entry in the virtual disk table. A row in this table cannot be
        created or deleted by SNMP operations on columns of the table.
        "
    INDEX         { virtualDiskNumber }
    ::= { virtualDiskTable 1 }
    
virtualDiskNumber OBJECT-TYPE
    SYNTAX          INTEGER (1..100000000)
    ACCESS          read-only
    STATUS          mandatory
    DESCRIPTION
        "Instance number of this virtual disk entry.
        "
        ::= { virtualDiskTableEntry 1 }

virtualDiskName OBJECT-TYPE    
    SYNTAX          DisplayString
    ACCESS          read-only
    STATUS          mandatory
    DESCRIPTION
        "The virtual disk's label as entered by the user.
        "
    ::= { virtualDiskTableEntry 2 }

virtualDiskState OBJECT-TYPE
    SYNTAX          INTEGER
                    {
                    unknown(1),
                    online(2),
                    failed(3),
                    degraded(4)
                    }
    ACCESS          read-only
    STATUS          mandatory
    DESCRIPTION
        "The current state of this virtual disk
        (which includes any member physical disks.)
        Possible states:
        1: The current state could not be determined.
        2: The virtual disk is operating normally or optimally.
        3: The virtual disk has encountered a failure. The data on disk 
        is lost or is about to be lost.
        4: The virtual disk encounterd a failure with one or all of the 
        constituent redundant physical disks. The data on the virtual 
        disk might no longer be fault tolerant.
        "
    ::= { virtualDiskTableEntry 4 }

virtualDiskSizeInMB OBJECT-TYPE
    SYNTAX          INTEGER
    ACCESS          read-only
    STATUS          mandatory
    DESCRIPTION
        "The size of the virtual disk in megabytes.
        "
    ::= { virtualDiskTableEntry 6 }

virtualDiskWritePolicy OBJECT-TYPE           
    SYNTAX          INTEGER
                    {
                    writeThrough(1),
                    writeBack(2),
                    writeBackForce(3)
                    }
    ACCESS          read-only
    STATUS          mandatory
    DESCRIPTION
        "The write policy used by the controller for write operations on 
        this virtual disk.
        Possible values:
        1: Write Through.
        2: Write Back.
        3: Force Write Back.
        "
    ::= { virtualDiskTableEntry 10 }

virtualDiskReadPolicy OBJECT-TYPE        
    SYNTAX          INTEGER
                    {
                    noReadAhead(1),
                    readAhead(2),
                    adaptiveReadAhead(3)
                    }
    ACCESS          read-only
    STATUS          mandatory
    DESCRIPTION
        "The read policy used by the controller for read operations on 
        this virtual disk.
        Possible values:
        1: No Read Ahead.
        2: Read Ahead.
        3: Adaptive Read Ahead.
        "
    ::= { virtualDiskTableEntry 11 }

virtualDiskLayout OBJECT-TYPE            
    SYNTAX          INTEGER
                    {
                    other(1),
                    r0(2),
                    r1(3),
                    r5(4),
                    r6(5),
                    r10(6),
                    r50(7),
                    r60(8),
                    concatRaid1(9),
                    concatRaid5(10)
                    }
    ACCESS          read-only
    STATUS          mandatory
    DESCRIPTION
        "The virtual disk's RAID type.
         Possible values:
         1: Not one of the following
         2: RAID-0
         3: RAID-1
         4: RAID-5
         5: RAID-6
         6: RAID-10
         7: RAID-50
         8: RAID-60
         9: Concatenated RAID 1
        10: Concatenated RAID 5
        "
    ::= { virtualDiskTableEntry 13 }

virtualDiskStripeSize OBJECT-TYPE        
    SYNTAX          INTEGER
                    {
                    other(1),
                    default(2),
                    fiveHundredAndTwelvebytes(3),
                    oneKilobytes(4),
                    twoKilobytes(5),
                    fourKilobytes(6),
                    eightKilobytes(7),
                    sixteenKilobytes(8),
                    thirtyTwoKilobytes(9),
                    sixtyFourKilobytes(10),
                    oneTwentyEightKilobytes(11),
                    twoFiftySixKilobytes(12),
                    fiveOneTwoKilobytes(13),
                    oneMegabye(14),
                    twoMegabytes(15),
                    fourMegabytes(16),
                    eightMegabytes(17),
                    sixteenMegabytes(18)
                    }
    ACCESS          read-only
    STATUS          mandatory
    DESCRIPTION
        "The stripe size of this virtual disk.
        Possible values:
        1: Not one of the following
        2: Default.
        3: 512 bytes
        4: 1 kB,
        5: 2 kB,
        6: 4 kB,
        7: 8 kB,
        8: 16 kB,
        9: 32 kB,
        10: 64 kB,
        11: 128 kB,
        12: 256 kB,
        13: 512 kB,
        14: 1 MB,
        15: 2 MB,
        16: 4 MB,
        17: 8 MB,
        18: 16 MB
        "
    ::= { virtualDiskTableEntry 14 }

virtualDiskComponentStatus OBJECT-TYPE
    SYNTAX          ObjectStatusEnum
    ACCESS          read-only
    STATUS          mandatory
    DESCRIPTION
        "The status of the virtual disk itself without the 
        propagation of any contained component status.
        Possible values:
        1: Other.
        2: Unknown.
        3: OK.
        4: Non-critical .
        5: Critical.
        6: Non-recoverable.
        "
    ::= { virtualDiskTableEntry 20 }

virtualDiskBadBlocksDetected OBJECT-TYPE    
    SYNTAX          BooleanType
    ACCESS          read-only
    STATUS          mandatory
    DESCRIPTION
        "Indicates whether the virtual disk has bad blocks.
        "
    ::= { virtualDiskTableEntry 23 }

virtualDiskSecured OBJECT-TYPE            
    SYNTAX          BooleanType
    ACCESS          read-only
    STATUS          mandatory
    DESCRIPTION
        "Indicates whether the virtual disk is secured or not.
        "
    ::= { virtualDiskTableEntry 24 }

virtualDiskIsCacheCade OBJECT-TYPE        
    SYNTAX          BooleanType
    ACCESS          read-only
    STATUS          mandatory
    DESCRIPTION
        "Indicates whether the virtual disk is being used as a secondary 
        cache by the controller.
        "
    ::= { virtualDiskTableEntry 25 }

virtualDiskDiskCachePolicy OBJECT-TYPE        
    SYNTAX          INTEGER
                    {
                    enabled(1),
                    disabled(2),
                    defullt(3)
                    }
    ACCESS          read-only
    STATUS          mandatory
    DESCRIPTION
        "The cache policy of the physical disks that are 
        part of this virtual disk 
        Possible values:
        1: Enabled.
        2: Disabled.
        3: Default.
        "
    ::= { virtualDiskTableEntry 26 }

virtualDiskOperationalState OBJECT-TYPE
    SYNTAX          INTEGER
                    {
                    notApplicable(1),
                    reconstructing(2),
                    resynching(3),
                    initializing(4),
                    backgroundInit(5)
                    }
    ACCESS          read-only
    STATUS          mandatory
    DESCRIPTION
        "The state of the virtual disk when there are progressive
        operations ongoing.
        Possible values:
        1: There is no active operation running.
        2: The virtual disk configuration has changed.
        The physical disks included in the virtual disk are being 
        modified to support the new configuration.
        3: A Consistency Check (CC) is being performed 
        on the virtual disk.
        4: The virtual disk is being initialized.
        5: BackGround Initialization (BGI) is being performed 
        on the virtual disk.
        "
    ::= { virtualDiskTableEntry 30 }

virtualDiskProgress OBJECT-TYPE
    SYNTAX          INTEGER (0..100)
    ACCESS          read-only
    STATUS          mandatory
    DESCRIPTION
        "The progress percentage of the operation that is being 
        performed on the virtual disk. This is applicable 
        only if there is a progressive operations ongoing
        "
    ::= { virtualDiskTableEntry 31 }

virtualDiskAvailableProtocols OBJECT-TYPE    
    SYNTAX          DisplayString
    ACCESS          read-only
    STATUS          mandatory
    DESCRIPTION
        "List of protocols support by physical disks part of this virtual
        disk. For e.g. SAS for Serial Attached SCSI or SATA for 
        Serial Advanced Technology Attachment.
        "
    ::= { virtualDiskTableEntry 32 }

virtualDiskMediaType OBJECT-TYPE        
    SYNTAX          DisplayString
    ACCESS          read-only
    STATUS          mandatory
    DESCRIPTION
        "List of media types of the physical disks part of this virtual
        disk. For e.g. HDD for Hard Disk Drive or SSD for Solid State Device.
        "
    ::= { virtualDiskTableEntry 33 }

virtualDiskRemainingRedundancy OBJECT-TYPE    
    SYNTAX          INTEGER (0..2)
    ACCESS          read-only
    STATUS          mandatory
    DESCRIPTION
        "The number of physical disks which can be lost before the
        virtual disk loses its redundancy.
        "
    ::= { virtualDiskTableEntry 34 }

virtualDiskFQDD OBJECT-TYPE   
    SYNTAX          FQDDString
    ACCESS          read-only
    STATUS          mandatory
    DESCRIPTION
        "The virtual disk's Fully Qualified Device Descriptor (FQDD) as 
        represented in Storage Management.
        "
    ::= { virtualDiskTableEntry 35 }

virtualDiskDisplayName OBJECT-TYPE
    SYNTAX          DisplayString
    ACCESS          read-only
    STATUS          mandatory
    DESCRIPTION
        "The virtual disk's friendly FQDD as represented in Storage 
        Management.
        "
    ::= { virtualDiskTableEntry 36 }

virtualDiskT10PIStatus OBJECT-TYPE
    SYNTAX          INTEGER
                    {
                    other(1),
                    enabled(2),
                    disabled(3)
                    }
    ACCESS          read-only
    STATUS          mandatory
    DESCRIPTION
        "Indicates whether the virtual disk supports the T10 PI (Protection 
        Information). These protection fields are known as DIF 
        (Data Integrity Fields).
        Possible values:
        1: Not one of the following.
        2: Enabled.
        3: Disabled.
        "
    ::= { virtualDiskTableEntry 37 }

virtualDiskBlockSizeInBytes OBJECT-TYPE
    SYNTAX          INTEGER
    ACCESS          read-only
    STATUS          mandatory
    DESCRIPTION
        "The block size (in bytes) of the physical disk part of the virtual disk.
        Possible values:
        1: 512.
        2: 4096
        "
    ::= { virtualDiskTableEntry 38 }

virtualDiskAdapter1AccessPolicy OBJECT-TYPE
    SYNTAX          INTEGER
                    {
                    NoAccess (1), 
                    FullAccess (2)
                    }
    ACCESS          read-only
    STATUS          mandatory
    DESCRIPTION
        "Indicates the access policy of the virtual disk with the virtual
        adapters.
        Possible values:
        1: No Access.
        2: Full Access
        "
    ::= { virtualDiskTableEntry 39 }

virtualDiskAdapter2AccessPolicy OBJECT-TYPE
    SYNTAX          INTEGER
                    {
                    NoAccess (1), 
                    FullAccess (2)
                    }
    ACCESS          read-only
    STATUS          mandatory
    DESCRIPTION
        "Indicates the access policy of the virtual disk with the virtual
        adapters.
        Possible values:
        1: No Access.
        2: Full Access
        "
    ::= { virtualDiskTableEntry 40 }

virtualDiskAdapter3AccessPolicy OBJECT-TYPE
    SYNTAX          INTEGER
                    {
                    NoAccess (1), 
                    FullAccess (2)
                    }
    ACCESS          read-only
    STATUS          mandatory
    DESCRIPTION
        "Indicates the access policy of the virtual disk with the virtual
        adapters.
        Possible values:
        1: No Access.
        2: Full Access
        "
    ::= { virtualDiskTableEntry 41 }

virtualDiskAdapter4AccessPolicy OBJECT-TYPE
    SYNTAX          INTEGER
                    {
                    NoAccess (1), 
                    FullAccess (2)
                    }
    ACCESS          read-only
    STATUS          mandatory
    DESCRIPTION
        "Indicates the access policy of the virtual disk with the virtual
        adapters.
        Possible values:
        1: No Access.
        2: Full Access
        "
    ::= { virtualDiskTableEntry 42 }

virtualDiskCurrentActiveController OBJECT-TYPE   
    SYNTAX          FQDDString
    ACCESS          read-only
    STATUS          mandatory
    DESCRIPTION
        "Indicates the Fully Qualified Device Descriptor (FQDD) of 
        the current active controller.
        "
    ::= { virtualDiskTableEntry 43 }

virtualDiskFailoverController OBJECT-TYPE
    SYNTAX          FQDDString
    ACCESS          read-only
    STATUS          mandatory
    DESCRIPTION
        "Indicates the Fully Qualified Device Descriptor (FQDD) of 
        the failover controller.
        "
    ::= { virtualDiskTableEntry 44 }


-------------------------------------------------------------------------------
-- Enclosure Table
--
-- OID Format:.1.3.6.1.4.1.674.10892.2.6.1.20.130.3.1.<a>.<i1>
-------------------------------------------------------------------------------

EnclosureTableEntry                             ::=SEQUENCE { 
    enclosureNumber                             INTEGER,
    enclosureName                               DisplayString,
    enclosureState                              INTEGER,
    enclosureServiceTag                         DisplayString,
    enclosureAssetTag                           DisplayString,
    enclosureConnectedPort                      DisplayString,
    enclosureRollUpStatus                       ObjectStatusEnum,    
    enclosureComponentStatus                    ObjectStatusEnum, 
    enclosureFirmwareVersion                    DisplayString,
    enclosureSASAddress                         DisplayString,
    enclosureDriveCount                         INTEGER,
    enclosureTotalSlots                         INTEGER,
    enclosureFanCount                           DisplayString,
    enclosurePSUCount                           DisplayString,
    enclosureEMMCount                           DisplayString,
    enclosureTempProbeCount                     DisplayString,
    enclosureRedundantPath                      DisplayString,
    enclosurePosition                           DisplayString,
    enclosureBackplaneBayID                     DisplayString,
    enclosureFQDD                               FQDDString,
    enclosureDisplayName                        DisplayString,
    enclosureType	                        INTEGER
}

enclosureTable OBJECT-TYPE
    SYNTAX          SEQUENCE OF EnclosureTableEntry
    ACCESS          not-accessible
    STATUS          mandatory
    DESCRIPTION
        "A table of managed enclosures/backplanes. The number of entries is 
        related to number of internal backplane(s) discovered in the system 
        and external storage enclosure(s) attached to the system..
        The maximum number of entries is implementation dependent.
        Note: The properties in this table may not be applicable to all 
        entries.
        "
    ::= { physicalDevices 3 }

enclosureTableEntry OBJECT-TYPE
    SYNTAX          EnclosureTableEntry
    ACCESS          not-accessible
    STATUS          mandatory
    DESCRIPTION
        "An entry in the enclosure table. A row in this table cannot be
        created or deleted by SNMP operations on columns of the table.
        "
    INDEX { enclosureNumber }
    ::= { enclosureTable 1 }

enclosureNumber OBJECT-TYPE    
    SYNTAX          INTEGER (1..255)
    ACCESS          read-only
    STATUS          mandatory
    DESCRIPTION
        "Instance number of this enclossre/backplane.
        "
    ::= { enclosureTableEntry 1 }

enclosureName OBJECT-TYPE        
    SYNTAX          DisplayString
    ACCESS          read-only
    STATUS          mandatory
    DESCRIPTION
        "The enclosure/backplane's name as represented in Storage Management.
        "
    ::= { enclosureTableEntry 2 }

enclosureState OBJECT-TYPE        
    SYNTAX          INTEGER
                    {
                    unknown(1),
                    ready(2),
                    failed(3),
                    missing(4),
                    degraded(5)
                    foreign(6)
                    offline(7)
                    online(8)
                    blocked(9)
                    }
    ACCESS          read-only
    STATUS          mandatory
    DESCRIPTION
        "The current state of this enclosure/backplane.
        Possible states:
        1: The current state could not be determined.
        2: The enclosure is operating normally.
        3: The enclosure has encountered a hardware problem or is not 
        responding.
        4: The enclosure is no longer connected to the controller or 
        there exists a problem communicating to the enclosure.
        5: The enclosure is unstable.
        6: The enclosure is inactive due to being configured by another
        controller.
        7: The enclosure is offline and inaccessible. 
        8: The enclosure is online and accessible.
        9: The enclosure is currently blocked by another controller.
        "
    ::= { enclosureTableEntry 4 }

enclosureServiceTag OBJECT-TYPE    
    SYNTAX          DisplayString
    ACCESS          read-only
    STATUS          mandatory
    DESCRIPTION
        "Enclosure identification used when consulting customer support.
        "
    ::= { enclosureTableEntry 8 }

enclosureAssetTag OBJECT-TYPE        
    SYNTAX          DisplayString
    ACCESS          read-only
    STATUS          mandatory
    DESCRIPTION
        "The asset tag information for the enclosure."
    ::= { enclosureTableEntry 9 }

enclosureConnectedPort OBJECT-TYPE    
    SYNTAX          DisplayString
    ACCESS          read-only
    STATUS          mandatory
    DESCRIPTION
        "The port on the controller to which the 
        storage enclosure is connected.
        "
    ::= { enclosureTableEntry 19 }

enclosureRollUpStatus OBJECT-TYPE    
    SYNTAX          ObjectStatusEnum
    ACCESS          read-only
    STATUS          mandatory
    DESCRIPTION
        "Severity of the enclosure/backplane state.
        This is the combined status of the enclosure and its sub-components.
        Possible values:
        1: Other.
        2: Unknown.
        3: OK.
        4: Non-critical.
        5: Critical.
        6: Non-recoverable.
        "
    ::= { enclosureTableEntry 23 }

enclosureComponentStatus OBJECT-TYPE    
    SYNTAX          ObjectStatusEnum
    ACCESS          read-only
    STATUS          mandatory
    DESCRIPTION
        "The status of the enclosure/backplane.itself without the 
        propagation of any contained component status.
        Possible values:
        1: Other.
        2: Unknown.
        3: OK.
        4: Non-critical .
        5: Critical.
        6: Non-recoverable.
        "
    ::= { enclosureTableEntry 24 }

enclosureFirmwareVersion OBJECT-TYPE    
    SYNTAX          DisplayString
    ACCESS          read-only
    STATUS          mandatory
    DESCRIPTION
        "The firmware information for the enclosure/backplane.
        "
    ::= { enclosureTableEntry 26 }

enclosureSASAddress OBJECT-TYPE
    SYNTAX          DisplayString
    ACCESS          read-only
    STATUS          mandatory
    DESCRIPTION
        "The SAS address of the enclosure/backplane.
        "
    ::= { enclosureTableEntry 30 }

enclosureDriveCount OBJECT-TYPE        
    SYNTAX          INTEGER
    ACCESS          read-only
    STATUS          mandatory
    DESCRIPTION
        "The number of disks present in the enclosure/backplane.
        "    
    ::= { enclosureTableEntry 31 }

enclosureTotalSlots OBJECT-TYPE    
    SYNTAX          INTEGER
    ACCESS          read-only
    STATUS          mandatory
    DESCRIPTION
        "The total physical drive slots in a storage enclosure 
        or server backplane.
        "
    ::= { enclosureTableEntry 32 }

enclosureFanCount OBJECT-TYPE        
    SYNTAX          DisplayString
    ACCESS          read-only
    STATUS          mandatory
    DESCRIPTION
        "The number of fans present in the storage enclosure.
        "    
    ::= { enclosureTableEntry 40 }

enclosurePSUCount OBJECT-TYPE        
    SYNTAX          DisplayString
    ACCESS          read-only
    STATUS          mandatory
    DESCRIPTION
        "The number of Power Supply Units (PSU) present 
        in the storage enclosure.
        "    
    ::= { enclosureTableEntry 41 }

enclosureEMMCount OBJECT-TYPE        
    SYNTAX          DisplayString
    ACCESS          read-only
    STATUS          mandatory
    DESCRIPTION
        "The number of Enclosure Management Modules (EMM) 
        present in the storage enclosure.
        "    
    ::= { enclosureTableEntry 42 }

enclosureTempProbeCount OBJECT-TYPE
    SYNTAX          DisplayString
    ACCESS          read-only
    STATUS          mandatory
    DESCRIPTION
        "The number of temperature sensing devices 
        present in the storage enclosure.
        "
    ::= { enclosureTableEntry 43 }

enclosureRedundantPath OBJECT-TYPE    
    SYNTAX          DisplayString
    ACCESS          read-only
    STATUS          mandatory
    DESCRIPTION
        "Indicates whether the controller has multiply paths to 
        reach the storage enclosure.
        "
    ::= { enclosureTableEntry 44 }

enclosurePosition OBJECT-TYPE        
     SYNTAX         DisplayString
     ACCESS         read-only
     STATUS         mandatory
     DESCRIPTION
         "The possition of the storage enclosure within a daisy chain.
         "
    ::= { enclosureTableEntry 45 }

enclosureBackplaneBayID OBJECT-TYPE    
    SYNTAX          DisplayString
    ACCESS          read-only
    STATUS          mandatory
    DESCRIPTION
        "The unique bay ID of the backplane.
        "
    ::= { enclosureTableEntry 46 }

enclosureFQDD OBJECT-TYPE        
    SYNTAX          FQDDString
    ACCESS          read-only
    STATUS          mandatory
    DESCRIPTION
        "The enclosure/backplane's Fully Qualified Device Descriptor (FQDD) 
        as represented in Storage Management.
        "
    ::= { enclosureTableEntry 47 }
    
enclosureDisplayName OBJECT-TYPE    
    SYNTAX          DisplayString
    ACCESS          read-only
    STATUS          mandatory
    DESCRIPTION
        "The enclosure/backplane's friendly FQDD as represented in 
        Storage Management.
        "
    ::= { enclosureTableEntry 48 }

enclosureType OBJECT-TYPE        
    SYNTAX          INTEGER
                    {
                    other(1),
                    notApplicable(2),
                    sassata(3),
                    pcie(4),
                    universal(5)
                    }
    ACCESS          read-only
    STATUS          mandatory
    DESCRIPTION
        "The protocol supported by the backplane.
        Possible states:
        1: Not one of the following or could not be determined.
        2: Not applicable (i.e. object is not a backplane).
        3: Supports SAS/SATA.
        4: Supports PCIe.
        5: Both SAS/SATA and PCIe.
        "
    ::= { enclosureTableEntry 49 }


-------------------------------------------------------------------------------
-- Enclosure Management Module Table
--
-- OID Format:.1.3.6.1.4.1.674.10892.2.6.1.20.130.13.1.<a>.<i1>
-------------------------------------------------------------------------------

EnclosureManagementModuleTableEntry             ::=SEQUENCE { 
    enclosureManagementModuleNumber             INTEGER,
    enclosureManagementModuleName               DisplayString,
    enclosureManagementModuleState              INTEGER,
    enclosureManagementModulePartNumber         DisplayString,
    enclosureManagementModuleFWVersion          DisplayString,
    enclosureManagementModuleComponentStatus    ObjectStatusEnum, 
    enclosureManagementModuleFQDD               FQDDString,
    enclosureManagementModuleDisplayName        DisplayString
}

enclosureManagementModuleTable OBJECT-TYPE
    SYNTAX          SEQUENCE OF EnclosureManagementModuleTableEntry
    ACCESS          not-accessible
    STATUS          mandatory
    DESCRIPTION
        "A table of managed Enclosure Management Modules (EMM) 
        in the external storage enclosure(s). The number of 
        entries is related to number of enclosure management modules
        discovered in the enclosure(s). The maximum number of entries 
        is implementation dependent.
        Note: The properties in this table may not be applicable to all 
        entries.
        "
    ::= { physicalDevices 13 }

enclosureManagementModuleTableEntry OBJECT-TYPE
    SYNTAX          EnclosureManagementModuleTableEntry
    ACCESS          not-accessible
    STATUS          mandatory
    DESCRIPTION
        "An entry in the enclosure management module table. A row in 
        this table cannot be created or deleted by SNMP operations 
        on columns of the table.
        "
    INDEX { enclosureManagementModuleNumber }
    ::= { enclosureManagementModuleTable 1 }

enclosureManagementModuleNumber OBJECT-TYPE
    SYNTAX          INTEGER (1..255)
    ACCESS          read-only
    STATUS          mandatory
    DESCRIPTION
        "Instance number of this enclosure management module.
        "
    ::= { enclosureManagementModuleTableEntry 1 }

enclosureManagementModuleName OBJECT-TYPE        
    SYNTAX          DisplayString
    ACCESS          read-only
    STATUS          mandatory
    DESCRIPTION
        "The enclosure management module's name as 
        represented in Storage Management.
        "
    ::= { enclosureManagementModuleTableEntry 2 }
 
enclosureManagementModuleState OBJECT-TYPE    
    SYNTAX          INTEGER
                    {
                    unknown(1),
                    ready(2),
                    failed(3),
                    missing(4),
                    degraded(5)
                    }
    ACCESS          read-only
    STATUS          mandatory
    DESCRIPTION
        "The current state of this enclosure management module.
        Possible states:
        1: The current state could not be determined.
        2: The enclosure management module is operating normally.
        3: The enclosure management module has encountered a 
        hardware problem or is not responding.
        4: The enclosure management module is no longer connected
        to the enclosure or there exists a problem communicating to it.
        5: The enclosure management module is unstable.
        "
    ::= { enclosureManagementModuleTableEntry 4 }

enclosureManagementModulePartNumber OBJECT-TYPE        
    SYNTAX          DisplayString
    ACCESS          read-only
    STATUS          mandatory
    DESCRIPTION
        "The part number of the enclosure management module.
        "
    ::= { enclosureManagementModuleTableEntry 6 }
 
enclosureManagementModuleFWVersion OBJECT-TYPE        
    SYNTAX          DisplayString
    ACCESS          read-only
    STATUS          mandatory
    DESCRIPTION
        "Firmware version of the enclosure management module.
        "    
    ::= { enclosureManagementModuleTableEntry 8 }

enclosureManagementModuleComponentStatus OBJECT-TYPE
    SYNTAX          ObjectStatusEnum
    ACCESS          read-only
    STATUS          mandatory
    DESCRIPTION
        "The status of the enclosure management module.itself without the 
        propagation of any contained component status.
        Possible values:
        1: Other.
        2: Unknown.
        3: OK.
        4: Non-critical .
        5: Critical.
        6: Non-recoverable.
        "
    ::= { enclosureManagementModuleTableEntry 11 }

enclosureManagementModuleFQDD OBJECT-TYPE        
    SYNTAX          FQDDString
    ACCESS          read-only
    STATUS          mandatory
    DESCRIPTION
        "The enclosure management module's Fully Qualified Device 
        Descriptor (FQDD) as represented in Storage Management.
        "
    ::= { enclosureManagementModuleTableEntry 15 }

enclosureManagementModuleDisplayName OBJECT-TYPE    
    SYNTAX          DisplayString
    ACCESS          read-only
    STATUS          mandatory
    DESCRIPTION
        "The enclosure management module's friendly FQDD as represented in 
        Storage Management.
        "
    ::= { enclosureManagementModuleTableEntry 16 }



-------------------------------------------------------------------------------
-- Enclosure Fan Table
--
-- OID Format:.1.3.6.1.4.1.674.10892.2.6.1.20.130.7.1.<a>.<i1>
-------------------------------------------------------------------------------

EnclosureFanTableEntry                          ::=SEQUENCE { 
    enclosureFanNumber                          INTEGER,
    enclosureFanName                            DisplayString,
    enclosureFanState                           INTEGER,
    enclosureFanSpeed                           INTEGER,
    enclosureFanComponentStatus                 ObjectStatusEnum, 
    enclosureFanFQDD                            FQDDString,
    enclosureFanDisplayName                     DisplayString
}

enclosureFanTable OBJECT-TYPE
    SYNTAX          SEQUENCE OF EnclosureFanTableEntry
    ACCESS          not-accessible
    STATUS          mandatory
    DESCRIPTION
        "A table of managed fans in the external storage enclosure(s). 
        The number of entries is related to number of fans discovered in 
        the enclosure(s). The maximum number of entries is implementation 
        dependent.
        Note: The properties in this table may not be applicable to all 
        entries.
        "
    ::= { physicalDevices 7 }
    
enclosureFanTableEntry OBJECT-TYPE
    SYNTAX          EnclosureFanTableEntry
    ACCESS          not-accessible
    STATUS          mandatory
    DESCRIPTION
        "An entry in the fan table. A row in this table cannot be
        created or deleted by SNMP operations on columns of the table.
        "
    INDEX { enclosureFanNumber }
    ::= { enclosureFanTable 1 }

enclosureFanNumber OBJECT-TYPE
    SYNTAX          INTEGER (1..255)
    ACCESS          read-only
    STATUS          mandatory
    DESCRIPTION
        "Instance number of this fan.
        "
    ::= { enclosureFanTableEntry 1 }

enclosureFanName OBJECT-TYPE        
    SYNTAX          DisplayString
    ACCESS          read-only
    STATUS          mandatory
    DESCRIPTION
        "The fan's name as represented in Storage Management.
        "
    ::= { enclosureFanTableEntry 2 }

enclosureFanState OBJECT-TYPE
    SYNTAX          INTEGER
                    {
                    unknown(1),
                    ready(2),
                    failed(3),
                    missing(4),
                    degraded(5)
                    }
    ACCESS          read-only
    STATUS          mandatory
    DESCRIPTION
        "The current state of this fan.
        Possible states:
        1: The current state could not be determined.
        2: The fan is operating normally.
        3: The fan has encountered a hardware problem or is not 
        responding.
        4: The fan is no longer connected to the enclosure or 
        there exists a problem communicating to it.
        5: The fan is unstable.
        "
    ::= { enclosureFanTableEntry 4 }

enclosureFanSpeed OBJECT-TYPE            
    SYNTAX          INTEGER
    ACCESS          read-only
    STATUS          mandatory
    DESCRIPTION
        "Indicates the current relative speed of the fan in RPMs.
        "
    ::= { enclosureFanTableEntry 11 }

enclosureFanComponentStatus OBJECT-TYPE    
    SYNTAX          ObjectStatusEnum
    ACCESS          read-only
    STATUS          mandatory
    DESCRIPTION
        "The status of the fan itself without the 
        propagation of any contained component status.
        Possible values:
        1: Other.
        2: Unknown.
        3: OK.
        4: Non-critical .
        5: Critical.
        6: Non-recoverable.
        "
    ::= { enclosureFanTableEntry 15 }

enclosureFanFQDD OBJECT-TYPE
    SYNTAX          FQDDString
    ACCESS          read-only
    STATUS          mandatory
    DESCRIPTION
        "The fan's Fully Qualified Device Descriptor (FQDD) 
        as represented in Storage Management.
        "
    ::= { enclosureFanTableEntry 20 }

enclosureFanDisplayName OBJECT-TYPE
    SYNTAX          DisplayString
    ACCESS          read-only
    STATUS          mandatory
    DESCRIPTION
        "The fan's friendly FQDD as represented in 
        Storage Management.
        "
    ::= { enclosureFanTableEntry 21 }




-------------------------------------------------------------------------------
-- Enclosure Power Supply Table
--
-- OID Format:.1.3.6.1.4.1.674.10892.2.6.1.20.130.9.1.<a>.<i1>
-------------------------------------------------------------------------------
EnclosurePowerSupplyTableEntry                 ::=SEQUENCE { 
    enclosurePowerSupplyNumber                  INTEGER,
    enclosurePowerSupplyName                    DisplayString,
    enclosurePowerSupplyState                   INTEGER,
    enclosurePowerSupplyPartNumber              DisplayString,
    enclosurePowerSupplyComponentStatus         ObjectStatusEnum, 
    enclosurePowerSupplyFQDD                    FQDDString,
    enclosurePowerSupplyDisplayName             DisplayString
}

enclosurePowerSupplyTable OBJECT-TYPE
    SYNTAX          SEQUENCE OF EnclosurePowerSupplyTableEntry
    ACCESS          not-accessible
    STATUS          mandatory
    DESCRIPTION
        "A table of managed Power Supply Units(PSU) in the external 
        storage enclosure(s). The number of entries is related to number 
        of power supply unit(s) discovered in the enclosure(s). The 
        maximum number of entries is implementation 
        dependent.
        Note: The properties in this table may not be applicable to all 
        entries.
        "
    ::= { physicalDevices 9 }
    
enclosurePowerSupplyTableEntry OBJECT-TYPE
    SYNTAX          EnclosurePowerSupplyTableEntry
    ACCESS          not-accessible
    STATUS          mandatory
    DESCRIPTION
        "An entry in the power supply unit table. A row in this table cannot 
        be created or deleted by SNMP operations on columns of the table.
        "
    INDEX { enclosurePowerSupplyNumber }
    ::= { enclosurePowerSupplyTable 1 }

enclosurePowerSupplyNumber OBJECT-TYPE
    SYNTAX          INTEGER (1..255)
    ACCESS          read-only
    STATUS          mandatory
    DESCRIPTION
        "Instance number of this power supply unit.
        "
    ::= { enclosurePowerSupplyTableEntry 1 }

enclosurePowerSupplyName OBJECT-TYPE        
    SYNTAX          DisplayString
    ACCESS          read-only
    STATUS          mandatory
    DESCRIPTION
        "The power supply unit's name as represented in 
        Storage Management.
        "
    ::= { enclosurePowerSupplyTableEntry 2 }

enclosurePowerSupplyState OBJECT-TYPE        
    SYNTAX          INTEGER
                    {
                    unknown(1),
                    ready(2),
                    failed(3),
                    missing(4),
                    degraded(5)
                    }
    ACCESS          read-only
    STATUS          mandatory
    DESCRIPTION
        "The current state of this power supply unit.
        Possible states:
        1: The current state could not be determined.
        2: The power supply unit is operating normally.
        3: The power supply unit has encountered a hardware problem 
        or is not responding.
        4: The power supply unit is no longer connected to the enclosure 
        or there exists a problem communicating to it.
        5: The power supply unit is unstable.
        "
    ::= { enclosurePowerSupplyTableEntry 4 }

enclosurePowerSupplyPartNumber OBJECT-TYPE        
    SYNTAX          DisplayString
    ACCESS          read-only
    STATUS          mandatory
    DESCRIPTION
        "The part number of the power supply unit. 
        "
    ::= { enclosurePowerSupplyTableEntry 7 }

enclosurePowerSupplyComponentStatus OBJECT-TYPE     
    SYNTAX          ObjectStatusEnum
    ACCESS          read-only
    STATUS          mandatory
    DESCRIPTION
        "The status of the power supply unit itself without the 
        propagation of any contained component status.
        Possible values:
        1: Other.
        2: Unknown.
        3: OK.
        4: Non-critical .
        5: Critical.
        6: Non-recoverable.
        "
    ::= { enclosurePowerSupplyTableEntry 9 }

enclosurePowerSupplyFQDD OBJECT-TYPE        
    SYNTAX          FQDDString
    ACCESS          read-only
    STATUS          mandatory
    DESCRIPTION
        "The power supply unit's Fully Qualified Device Descriptor (FQDD)
        as represented in Storage Management.
        "
    ::= { enclosurePowerSupplyTableEntry 15 }

enclosurePowerSupplyDisplayName OBJECT-TYPE    
    SYNTAX          DisplayString
    ACCESS          read-only
    STATUS          mandatory
    DESCRIPTION
        "The power supply unit's friendly FQDD as represented in 
        Storage Management.
        "
    ::= { enclosurePowerSupplyTableEntry 16 }


-------------------------------------------------------------------------------
-- Enclosure Temperature Probe Table
--
-- OID Format:.1.3.6.1.4.1.674.10892.2.6.1.20.130.11.1.<a>.<i1>
-------------------------------------------------------------------------------
EnclosureTemperatureProbeTableEntry             ::=SEQUENCE { 
    enclosureTemperatureProbeNumber             INTEGER,
    enclosureTemperatureProbeName               DisplayString,
    enclosureTemperatureProbeState              INTEGER,
    enclosureTemperatureProbeMinWarningValue    INTEGER,
    enclosureTemperatureProbeMinCriticalValue   INTEGER,
    enclosureTemperatureProbeMaxWarningValue    INTEGER,
    enclosureTemperatureProbeMaxCriticalValue   INTEGER,
    enclosureTemperatureProbeCurValue           INTEGER,
    enclosureTemperatureProbeComponentStatus    ObjectStatusEnum, 
    enclosureTemperatureProbeFQDD               FQDDString,
    enclosureTemperatureProbeDisplayName        DisplayString
}

enclosureTemperatureProbeTable OBJECT-TYPE
    SYNTAX          SEQUENCE OF EnclosureTemperatureProbeTableEntry
    ACCESS          not-accessible
    STATUS          mandatory
    DESCRIPTION
        "A table of managed temperature probes in the external storage
        enclosure(s). The number of entries is related to number of 
        temperature probes discovered in the enclosure(s). The maximum 
        number of entries is implementation dependent.
        Note: The properties in this table may not be applicable to all 
        entries.
        "
    ::= { physicalDevices 11 }
    
enclosureTemperatureProbeTableEntry OBJECT-TYPE
    SYNTAX          EnclosureTemperatureProbeTableEntry
    ACCESS          not-accessible
    STATUS          mandatory
    DESCRIPTION
        "An entry in the temperature probe table. A row in this table cannot be
        created or deleted by SNMP operations on columns of the table.
        "
    INDEX { enclosureTemperatureProbeNumber }
    ::= { enclosureTemperatureProbeTable 1 }

enclosureTemperatureProbeNumber OBJECT-TYPE
    SYNTAX          INTEGER (1..255)
    ACCESS          read-only
    STATUS          mandatory
    DESCRIPTION
        "Instance number of this temperature probe.
        "
    ::= { enclosureTemperatureProbeTableEntry 1 }

enclosureTemperatureProbeName OBJECT-TYPE        
    SYNTAX          DisplayString
    ACCESS          read-only
    STATUS          mandatory
    DESCRIPTION
        "The temperature probe's name as represented in 
        Storage Management.
        "
    ::= { enclosureTemperatureProbeTableEntry 2 }

enclosureTemperatureProbeState OBJECT-TYPE    
    SYNTAX          INTEGER
                    {
                    unknown(1),
                    ready(2),
                    failed(3),
                    missing(4),
                    degraded(5)
                    overWarning(6)
                    underWarning(7)
                    }
    ACCESS          read-only
    STATUS          mandatory
    DESCRIPTION
        "The current state of this temperature probe.
        Possible states:
        1: The current state could not be determined.
        2: The temperature probe is operating normally.
        3: The temperature probe has encountered a hardware problem 
        or is not responding.
        4: The temperature probe is no longer connected to the enclosure 
        or there exists a problem communicating to it.
        5: The temperature probe is unstable.
        6: The temperature probe is Over Warning Temperature.
        7: The temperature probe is Under Warning Temperature.
        "
    ::= { enclosureTemperatureProbeTableEntry 4 }

enclosureTemperatureProbeMinWarningValue OBJECT-TYPE    
    SYNTAX          INTEGER
    ACCESS          read-only
    STATUS          mandatory
    DESCRIPTION
        "The minimum temperature that will force the probe into
        a warning state.
        "
    ::= { enclosureTemperatureProbeTableEntry 7 }

enclosureTemperatureProbeMinCriticalValue OBJECT-TYPE    
    SYNTAX          INTEGER
    ACCESS          read-only
    STATUS          mandatory
    DESCRIPTION
        "The minimum temperature that will force the probe into
        a error state.
        "
    ::= { enclosureTemperatureProbeTableEntry 8 }

enclosureTemperatureProbeMaxWarningValue OBJECT-TYPE    
    SYNTAX          INTEGER
    ACCESS          read-only
    STATUS          mandatory
    DESCRIPTION
        "The maximum temperature that will force the probe into
        a warning state.
        "
    ::= { enclosureTemperatureProbeTableEntry 9 }

enclosureTemperatureProbeMaxCriticalValue OBJECT-TYPE    
    SYNTAX          INTEGER
    ACCESS          read-only
    STATUS          mandatory
    DESCRIPTION
        "The maximum temperature that will force the probe into
        a warning state.
        "
    ::= { enclosureTemperatureProbeTableEntry 10 }
    
enclosureTemperatureProbeCurValue OBJECT-TYPE        
    SYNTAX          INTEGER
    ACCESS          read-only
    STATUS          mandatory
    DESCRIPTION
        "The maximum temperature that will force the probe into
        a warning state.
        "
    ::= { enclosureTemperatureProbeTableEntry 11 }

enclosureTemperatureProbeComponentStatus OBJECT-TYPE
    SYNTAX          ObjectStatusEnum
    ACCESS          read-only
    STATUS          mandatory
    DESCRIPTION
        "The status of the enclosure management module.itself without the 
        propagation of any contained component status.
        Possible values:
        1: Other.
        2: Unknown.
        3: OK.
        4: Non-critical .
        5: Critical.
        6: Non-recoverable.
        "
    ::= { enclosureTemperatureProbeTableEntry 13 }    
    
enclosureTemperatureProbeFQDD OBJECT-TYPE
    SYNTAX          FQDDString
    ACCESS          read-only
    STATUS          mandatory
    DESCRIPTION
        "The temperature probe's Fully Qualified Device Descriptor (FQDD)
        as represented in Storage Management.
        "
    ::= { enclosureTemperatureProbeTableEntry 15 }
    
enclosureTemperatureProbeDisplayName OBJECT-TYPE    
    SYNTAX          DisplayString
    ACCESS          read-only
    STATUS          mandatory
    DESCRIPTION
        "The temperature probe's friendly FQDD as represented 
        in Storage Management.
        "
    ::= { enclosureTemperatureProbeTableEntry 16 }


	-------------------------------------------------------------------------------
	-- group: Chassis Alerts 1
	-------------------------------------------------------------------------------

            drsCASubSystem      OBJECT-TYPE
                SYNTAX		  DellString
                ACCESS		  read-only
                STATUS		  mandatory
                DESCRIPTION     "0020.0010.0001 This attribute defines the Sub-System Name of the CMC Alert"
               ::= { drsChassisAlertVariables 1 }

            drsCASSCurrStatus   OBJECT-TYPE
                SYNTAX		  DellStatus
                ACCESS		  read-only
                STATUS		  mandatory
                DESCRIPTION     "0020.0010.0002 This attribute defines the Current Status of the Alerting 
                                 Sub-System"
               ::= { drsChassisAlertVariables 2 }

            drsCASSPrevStatus   OBJECT-TYPE
                SYNTAX		  DellStatus
                ACCESS		  read-only
                STATUS		  mandatory
                DESCRIPTION     "0020.0010.0003 This attribute defines the Previous Status of the Alerting 
                                 Sub-System"
               ::= { drsChassisAlertVariables 3 }

            drsCASSChangeTime   OBJECT-TYPE
                SYNTAX		  TimeTicks
                ACCESS		  read-only
                STATUS		  mandatory
                DESCRIPTION     "0020.0010.0004 This attribute defines the Timestamp of Most Recent Change of 
                                 the Alerting Sub-System"
               ::= { drsChassisAlertVariables 4 }

            drsCAMessage        OBJECT-TYPE
                SYNTAX		  DellString
                ACCESS		  read-only
                STATUS		  mandatory
                DESCRIPTION     "0020.0010.0005 This attribute defines the CSSD message of the CMC Alert"
               ::= { drsChassisAlertVariables 5 }

            alertCMCTestTrap  TRAP-TYPE
                ENTERPRISE 	  drsOutofBandGroup
                DESCRIPTION   "The CMC has generated a test trap"
                --#TYPE "CMC Test Trap"
                --#SUMMARY "CMC Test Trap"
                --#SEVERITY INFORMATIONAL
                --#CATEGORY Error Events
               ::= 2000
              
            alertCMCNormalTrap  TRAP-TYPE
                ENTERPRISE  	  drsOutofBandGroup
                VARIABLES { 	  drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a return-to-normal or informational event."
                --#TYPE "CMC Return-to-Normal / Informational Trap"
                --#SUMMARY "Return-to-Normal / Informational Trap from CMC in system %s in location %s, message: %s"
                --#ARGUMENTS {0,1,7}
                --#SEVERITY NORMAL
                --#CATEGORY Error Events
               ::= 2002

            alertCMCWarningTrap TRAP-TYPE
                ENTERPRISE 	    drsOutofBandGroup
                VARIABLES {     drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a warning event."
                --#TYPE "CMC Warning Trap"
                --#SUMMARY "Warning Trap from CMC in system %s in location %s, message: %s"
                --#ARGUMENTS {0,1,7}
                --#SEVERITY WARNING
                --#CATEGORY Error Events
               ::= 2003

            alertCMCCriticalTrap TRAP-TYPE
                ENTERPRISE 	    drsOutofBandGroup
                VARIABLES { 	  drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a critical event."
                --#TYPE "CMC Critical Trap"
                --#SUMMARY "Critical Trap from CMC in system %s in location %s, message: %s"
                --#ARGUMENTS {0,1,7}
                --#SEVERITY CRITICAL
                --#CATEGORY Error Events
               ::= 2004

            alertCMCNonRecoverableTrap TRAP-TYPE
                ENTERPRISE 	    drsOutofBandGroup
                VARIABLES { 	  drsProductChassisName,
                                drsProductChassisLocation,
                                drsGlobalCurrStatus,
                                drsCASubSystem,
                                drsCASSCurrStatus,
                                drsCASSPrevStatus,
                                drsCASSChangeTime,
                                drsCAMessage }
                DESCRIPTION     "The CMC reported a catastrophic event."
                --#TYPE "CMC Non-Recoverable Trap"
                --#SUMMARY "Non-Recoverable Trap from CMC in system %s in location %s, message: %s"
                --#ARGUMENTS {0,1,7}
                --#SEVERITY NON-RECOVERABLE
                --#CATEGORY Error Events
               ::= 2005

	-------------------------------------------------------------------------------
	-- group: Chassis Alerts 2
	-------------------------------------------------------------------------------

    drsCA2MessageID     OBJECT-TYPE
        SYNTAX          DisplayString (SIZE (0..8))
        ACCESS          read-only
        STATUS          mandatory
        DESCRIPTION     "Message ID of the alert."
        ::= { drsChassisAlert2Variables 1 }

    drsCA2Message       OBJECT-TYPE
        SYNTAX          DellString
        ACCESS          read-only
        STATUS          mandatory
        DESCRIPTION     "Message describing the alert."
        ::= { drsChassisAlert2Variables 2 }

    drsCA2MessageArgs   OBJECT-TYPE
        SYNTAX          DellString
        ACCESS          read-only
        STATUS          mandatory
        DESCRIPTION     "Concatenated set of strings representing any message arguments
                         that were used to construct the alert message.  Each message
                         argument string is enclosed in double quotes, and there is a
                         comma after the ending double quote of each message argument
                         string, except the last one.  Any double quotes found within a
                         message argument string were preprocessed and changed to single
                         quotes."
        ::= { drsChassisAlert2Variables 3 }

    drsCA2AlertStatus   OBJECT-TYPE
        SYNTAX          DellStatus
        ACCESS          read-only
        STATUS          mandatory
        DESCRIPTION     "Status of the alert."
        ::= { drsChassisAlert2Variables 4 }

    drsCA2FQDD          OBJECT-TYPE
        SYNTAX          DisplayString (SIZE (0..512))
        ACCESS          read-only
        STATUS          mandatory
        DESCRIPTION     "Fully qualified device descriptor of device causing the alert."
        ::= { drsChassisAlert2Variables 5 }

    ------------------------------------------------------------------------------
    -- Chassis Alerts 2: System: Amperage Probe Traps
    --
    -- Category: System/1
    -- Subcategory: AMP/16
    ------------------------------------------------------------------------------

    alert2AmperageProbeNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Current sensor reading is within range."
        --#TYPE       "System: Amperage Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2179

    alert2AmperageProbeWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Current sensor has detected a warning value."
        --#TYPE       "System: Amperage Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2178

    alert2AmperageProbeFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Current sensor has detected a failure value."
        --#TYPE       "System: Amperage Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2177
        
    ------------------------------------------------------------------------------
    -- Chassis Alerts 2: System: Battery Traps
    --
    -- Category: System/1
    -- Subcategory: BAT/22
    ------------------------------------------------------------------------------

    alert2BatteryNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Battery state has returned to normal;
             or battery presence had been detected."
        --#TYPE       "System: Battery Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2227

    alert2BatteryWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Battery is low."
        --#TYPE       "System: Battery Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2226

    alert2BatteryFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Battery has failed or battery is absent."
        --#TYPE       "System: Battery Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2225

    ------------------------------------------------------------------------------
    -- Chassis Alerts 2: System: Cable Traps
    --
    -- Category: System/1
    -- Subcategory: CBL/43
    ------------------------------------------------------------------------------

    alert2CableFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Cable failure."
        --#TYPE       "System: Cable Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2393

    ------------------------------------------------------------------------------
    -- Chassis Alerts 2: System: CMC Traps
    --
    -- Category: System/1
    -- Subcategory: CMC/62
    ------------------------------------------------------------------------------

    alert2CMCWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller detected a warning."
        --#TYPE       "System: CMC Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2546

    alert2CMCFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller detected an error."
        --#TYPE       "System: CMC Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2545

    ------------------------------------------------------------------------------
    -- Chassis Alerts 2: System: Fan Traps
    --
    -- Category: System/1
    -- Subcategory: FAN/13
    ------------------------------------------------------------------------------

    alert2FanInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Fan information."
        --#TYPE       "System: Fan Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2155

    alert2FanWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Fan warning."
        --#TYPE       "System: Fan Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2154

    alert2FanFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Fan failure."
        --#TYPE       "System: Fan Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2153

    ------------------------------------------------------------------------------
    -- Chassis Alerts 2: System: Hardware Configuration Traps
    --
    -- Category: System/1
    -- Subcategory: HWC/35
    ------------------------------------------------------------------------------

    alert2HardwareConfigurationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Hardware configuration information."
        --#TYPE       "System: Hardware Configuration Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2331

    alert2HardwareConfigurationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Hardware configuration warning."
        --#TYPE       "System: Hardware Configuration Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2330

    alert2HardwareConfigurationFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Hardware configuration failure or critical event."
        --#TYPE       "System: Hardware Configuration Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2329

    ------------------------------------------------------------------------------
    -- Chassis Alerts 2: System: IO Virtualization Traps
    --
    -- Category: System/1
    -- Subcategory: IOV/63
    ------------------------------------------------------------------------------

    alert2IOVirtualizationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization information."
        --#TYPE       "System: IO Virtualization Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2555

    alert2IOVirtualizationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization warning."
        --#TYPE       "System: IO Virtualization Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2554

    alert2IOVirtualizationFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization failure or critical event."
        --#TYPE       "System: IO Virtualization Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2553

    ------------------------------------------------------------------------------
    -- Chassis Alerts 2: System: Link Status Traps
    --
    -- Category: System/1
    -- Subcategory: LNK/25
    ------------------------------------------------------------------------------

    alert2LinkStatusInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Link status information."
        --#TYPE       "System: Link Status Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2251

    alert2LinkStatusWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Link status warning."
        --#TYPE       "System: Link Status Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2250

    alert2LinkStatusFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Link status failure or critical event."
        --#TYPE       "System: Link Status Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2249

    ------------------------------------------------------------------------------
    -- Chassis Alerts 2: System: PCI Device Traps
    --
    -- Category: System/1
    -- Subcategory: PCI/46
    ------------------------------------------------------------------------------

    alert2PCIDeviceInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device information."
        --#TYPE       "System: PCI Device Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2419

    alert2PCIDeviceWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device warning."
        --#TYPE       "System: PCI Device Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2418

    alert2PCIDeviceFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device failure or critical event."
        --#TYPE       "System: PCI Device Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2417

    ------------------------------------------------------------------------------
    -- Chassis Alerts 2: System: Power Supply Traps
    --
    -- Category: System/1
    -- Subcategory: PSU/17
    ------------------------------------------------------------------------------

    alert2PowerSupplyNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power supply has returned to normal."
        --#TYPE       "System: Power Supply Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2187

    alert2PowerSupplyWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power supply has detected a warning."
        --#TYPE       "System: Power Supply Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2186

    alert2PowerSupplyFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power supply has detected a failure."
        --#TYPE       "System: Power Supply Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2185

    ------------------------------------------------------------------------------
    -- Chassis Alerts 2: System: Power Supply Absent Traps
    --
    -- Category: System/1
    -- Subcategory: PSUA/52
    ------------------------------------------------------------------------------

    alert2PowerSupplyAbsent TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power supply is absent."
        --#TYPE       "System: Power Supply Absent"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2465

    ------------------------------------------------------------------------------
    -- Chassis Alerts 2: System: Power Usage Traps
    --
    -- Category: System/1
    -- Subcategory: PWR/28
    ------------------------------------------------------------------------------

    alert2PowerUsageInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage information."
        --#TYPE       "System: Power Usage Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2275

    alert2PowerUsageWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage warning."
        --#TYPE       "System: Power Usage Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2274

    alert2PowerUsageFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage failure."
        --#TYPE       "System: Power Usage Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2273

    ------------------------------------------------------------------------------
    -- Chassis Alerts 2: System: Redundancy Traps
    --
    -- Category: System/1
    -- Subcategory: RDU/53
    ------------------------------------------------------------------------------

    alert2RedundancyInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Redundancy information."
        --#TYPE       "System: Redundancy Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2475

    alert2RedundancyDegraded TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Redundancy is degraded."
        --#TYPE       "System: Redundancy Degraded"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2474

    alert2RedundancyLost TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Redundancy is lost."
        --#TYPE       "System: Redundancy Lost"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2473

    ------------------------------------------------------------------------------
    -- Chassis Alerts 2: System: Security Event Traps
    --
    -- Category: System/1
    -- Subcategory: SEC/42
    ------------------------------------------------------------------------------

    alert2SecurityInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Security information."
        --#TYPE       "System: Security Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2387

    alert2SecurityWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Security warning."
        --#TYPE       "System: Security Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2386

    alert2SecurityFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Security failure or critical event."
        --#TYPE       "System: Security Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 2385

    ------------------------------------------------------------------------------
    -- Chassis Alerts 2: System: System Event Log Traps
    --
    -- Category: System/1
    -- Subcategory: SEL/41
    ------------------------------------------------------------------------------

    alert2SystemEventLogInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "System Event Log information."
        --#TYPE       "System: System Event Log Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2379

    alert2SystemEventLogWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "System Event Log warning."
        --#TYPE       "System: System Event Log Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2378

    alert2SystemEventLogFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "System Event Log failure or critical event."
        --#TYPE       "System: System Event Log Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 2377

    ------------------------------------------------------------------------------
    -- Chassis Alerts 2: System: Software Configuration Traps
    --
    -- Category: System/1
    -- Subcategory: SWC/36
    ------------------------------------------------------------------------------

    alert2SoftwareConfigurationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration information."
        --#TYPE       "System: Software Configuration Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2339

    alert2SoftwareConfigurationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration warning."
        --#TYPE       "System: Software Configuration Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2338

    alert2SoftwareConfigurationFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration failure."
        --#TYPE       "System: Software Configuration Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2337

    ------------------------------------------------------------------------------
    -- Chassis Alerts 2: System: Temperature Probe Traps
    --
    -- Category: System/1
    -- Subcategory: TMP/14
    ------------------------------------------------------------------------------

    alert2TemperatureProbeNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Temperature sensor value is within range."
        --#TYPE       "System: Temperature Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2163

    alert2TemperatureProbeWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Temperature sensor has detected a warning value."
        --#TYPE       "System: Temperature Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2162

    alert2TemperatureProbeFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Temperature sensor has detected a failure value."
        --#TYPE       "System: Temperature Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2161

    ------------------------------------------------------------------------------
    -- Chassis Alerts 2: System: Voltage Probe Traps
    --
    -- Category: System/1
    -- Subcategory: VLT/15
    ------------------------------------------------------------------------------

    alert2VoltageProbeNormal TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Voltage sensor reading is within range."
        --#TYPE       "System: Voltage Normal"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 2171

    alert2VoltageProbeWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Voltage sensor has detected a warning value."
        --#TYPE       "System: Voltage Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 2170

    alert2VoltageProbeFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Voltage sensor has detected a failure value."
        --#TYPE       "System: Voltage Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 2169

    -------------------------------------------------------------------------------
    -- Chassis Alerts 2: Storage: Battery Traps
    --
    -- Category: Storage/2
    -- Subcategory: BAT/22
    -------------------------------------------------------------------------------

    alert2StorageBatteryInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Battery information."
        --#TYPE       "Storage: Battery Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4275

    alert2StorageBatteryWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Battery warning."
        --#TYPE       "Storage: Battery Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4274

    alert2StorageBatteryFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Battery failure."
        --#TYPE       "Storage: Battery Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4273

    ------------------------------------------------------------------------------
    -- Chassis Alerts 2: Storage: Controller Traps
    --
    -- Category: Storage/2
    -- Subcategory: CTL/29
    ------------------------------------------------------------------------------

    alert2StorageControllerInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Controller information."
        --#TYPE       "Storage: Controller Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4331

    alert2StorageControllerWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Controller warning."
        --#TYPE       "Storage: Controller Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4330

    alert2StorageControllerFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Controller failure."
        --#TYPE       "Storage: Controller Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4329

    ------------------------------------------------------------------------------
    -- Chassis Alerts 2: Storage: Enclosure Traps
    --
    -- Category: Storage/2
    -- Subcategory: ENC/30
    ------------------------------------------------------------------------------

    alert2StorageEnclosureInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Enclosure information."
        --#TYPE       "Storage: Enclosure Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4339

    alert2StorageEnclosureWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Enclosure warning."
        --#TYPE       "Storage: Enclosure Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4338

    alert2StorageEnclosureFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Enclosure failure."
        --#TYPE       "Storage: Enclosure Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4337

    ------------------------------------------------------------------------------
    -- Chassis Alerts 2: Storage: Fan Traps
    --
    -- Category: Storage/2
    -- Subcategory: FAN/13
    ------------------------------------------------------------------------------

    alert2StorageFanInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Fan information."
        --#TYPE       "Storage: Fan Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4203

    alert2StorageFanWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Fan warning."
        --#TYPE       "Storage: Fan Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 4202

    alert2StorageFanFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Fan failure."
        --#TYPE       "Storage: Fan Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4201

    ------------------------------------------------------------------------------
    -- Chassis Alerts 2: Storage: Physical Disk Traps
    --
    -- Category: Storage/2
    -- Subcategory: PDR/31
    ------------------------------------------------------------------------------

    alert2StoragePhysicalDiskInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Physical disk information."
        --#TYPE       "Storage: Physical Disk Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4347

    alert2StoragePhysicalDiskWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Physical disk warning."
        --#TYPE       "Storage: Physical Disk Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4346

    alert2StoragePhysicalDiskFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Physical disk failure."
        --#TYPE       "Storage: Physical Disk Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4345

    ------------------------------------------------------------------------------
    -- Chassis Alerts 2: Storage: Power Supply Traps
    --
    -- Category: Storage/2
    -- Subcategory: PSU/17
    ------------------------------------------------------------------------------

    alert2StoragePowerSupplyInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Power supply information."
        --#TYPE       "Storage: Power Supply Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4235

    alert2StoragePowerSupplyWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Power supply warning."
        --#TYPE       "Storage: Power Supply Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4234

    alert2StoragePowerSupplyFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Power supply failure."
        --#TYPE       "Storage: Power Supply Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4233

    ------------------------------------------------------------------------------
    -- Chassis Alerts 2: Storage: Security Event Traps
    --
    -- Category: Storage/2
    -- Subcategory: SEC/42
    ------------------------------------------------------------------------------

    alert2StorageSecurityInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Security information."
        --#TYPE       "Storage: Security Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 4435

    alert2StorageSecurityWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Security warning."
        --#TYPE       "Storage: Security Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 4434

    alert2StorageSecurityFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Security failure or critical event."
        --#TYPE       "Storage: Security Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4433

    ------------------------------------------------------------------------------
    -- Chassis Alerts 2: Storage: Storage Management Status Traps
    --
    -- Category: Storage/2
    -- Subcategory: STOR/10
    ------------------------------------------------------------------------------

    alert2StorageManagementInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Management information.
            There is no global status change associated with this trap."
        --#TYPE       "Storage: Storage Management Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4179

    alert2StorageManagementWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Management has detected a device independent warning
            condition. There is no global status change associated with this
            trap."
        --#TYPE       "Storage: Storage Management Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4178

    alert2StorageManagementFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Storage Management has detected a device independent error condition.
            There is no global status change associated with this trap."
        --#TYPE       "Storage: Storage Management Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4177

    ------------------------------------------------------------------------------
    -- Chassis Alerts 2: Storage: Temperature Probe Traps
    --
    -- Category: Storage/2
    -- Subcategory: TMP/14
    ------------------------------------------------------------------------------

    alert2StorageTemperatureProbeInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Temperature probe information."
        --#TYPE       "Storage: Temperature Probe Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4211

    alert2StorageTemperatureProbeWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Temperature probe warning."
        --#TYPE       "Storage: Temperature Probe Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4210

    alert2StorageTemperatureProbeFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Temperature probe failure."
        --#TYPE       "Storage: Temperature Probe Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4209

    ------------------------------------------------------------------------------
    -- Chassis Alerts 2: Storage: Virtual Disk Traps
    --
    -- Category: Storage/2
    -- Subcategory: VDR/32
    ------------------------------------------------------------------------------

    alert2StorageVirtualDiskInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Virtual disk information."
        --#TYPE       "Storage: Virtual Disk Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      OPERATIONAL
        --#STATUS     MANDATORY
        ::= 4355

    alert2StorageVirtualDiskWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Virtual disk warning."
        --#TYPE       "Storage: Virtual Disk Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 4354

    alert2StorageVirtualDiskFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
             "Storage Virtual disk failure."
        --#TYPE       "Storage: Virtual Disk Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      FAILED
        --#STATUS     MANDATORY
        ::= 4353

    ------------------------------------------------------------------------------
    -- Chassis Alerts 2: Updates: Software Change Traps
    --
    -- Category: Updates/3
    -- Subcategory: SWU/21
    ------------------------------------------------------------------------------

    alert2SoftwareChangeUpdateWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software change update warning."
        --#TYPE       "Updates: Software Change Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 6314

    ------------------------------------------------------------------------------
    -- Chassis Alerts 2: Audit: CMC Traps
    --
    -- Category: Audit/4
    -- Subcategory: CMC/62
    ------------------------------------------------------------------------------

    alert2CMCAuditInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller audit information."
        --#TYPE       "Audit: CMC Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 8691

    alert2CMCAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller audit warning."
        --#TYPE       "Audit: CMC Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8690

    alert2CMCAuditFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Chassis Management Controller audit failure or critical event."
        --#TYPE       "Audit: CMC Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8689

    ------------------------------------------------------------------------------
    -- Chassis Alerts 2: Audit: IO Virtualization Traps
    --
    -- Category: Audit/4
    -- Subcategory: IOV/63
    ------------------------------------------------------------------------------

    alert2IOVirtualizationAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization audit warning."
        --#TYPE       "Audit: IO Virtualization Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8698

    ------------------------------------------------------------------------------
    -- Chassis Alerts 2: Audit: License Traps
    --
    -- Category: Audit/4
    -- Subcategory: LIC/40
    ------------------------------------------------------------------------------

    alert2LicenseInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "License information."
        --#TYPE       "Audit: License Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 8515

    alert2LicenseWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "License warning."
        --#TYPE       "Audit: License Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8514

    alert2LicenseFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "License failure."
        --#TYPE       "Audit: License Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8513

    ------------------------------------------------------------------------------
    -- Chassis Alerts 2: Audit: PCI Device Traps
    --
    -- Category: Audit/4
    -- Subcategory: PCI/46
    ------------------------------------------------------------------------------

    alert2PCIDeviceAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device audit warning."
        --#TYPE       "Audit: PCI Device Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8562

    ------------------------------------------------------------------------------
    -- Chassis Alerts 2: Audit: Power Supply Traps
    --
    -- Category: Audit/4
    -- Subcategory: PSU/17
    ------------------------------------------------------------------------------

    alert2PowerSupplyAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power Supply audit warning."
        --#TYPE       "Audit: Power Supply Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8330

    alert2PowerSupplyAuditFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power Supply audit failure or critical event."
        --#TYPE       "Audit: Power Supply Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8329

    ------------------------------------------------------------------------------
    -- Chassis Alerts 2: Audit: Power Usage Traps
    --
    -- Category: Audit/4
    -- Subcategory: PWR/28
    ------------------------------------------------------------------------------

    alert2PowerUsageAuditInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage audit information."
        --#TYPE       "Audit: Power Usage Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 8419

    alert2PowerUsageAuditWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage audit warning."
        --#TYPE       "Audit: Power Usage Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 8418

    alert2PowerUsageAuditFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Power usage audit failure or critical event."
        --#TYPE       "Audit: Power Usage Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8417

    ------------------------------------------------------------------------------
    -- Chassis Alerts 2: Audit: Software Change Traps
    --
    -- Category: Audit/4
    -- Subcategory: SWU/21
    ------------------------------------------------------------------------------

    alert2SoftwareChangeAuditFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software change audit failure or critical event."
        --#TYPE       "Audit: Software Change Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 8361

    ------------------------------------------------------------------------------
    -- Chassis Alerts 2: Configuration: IO Virtualization Traps
    --
    -- Category: Configuration/5
    -- Subcategory: IOV/63
    ------------------------------------------------------------------------------

    alert2IOVConfigurationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization configuration information."
        --#TYPE       "Configuration: IO Virtualization Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 10747

    alert2IOVConfigurationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "IO Virtualization configuration warning."
        --#TYPE       "Configuration: IO Virtualization Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 10746

    ------------------------------------------------------------------------------
    -- Chassis Alerts 2: Configuration: PCI Device Traps
    --
    -- Category: Configuration/5
    -- Subcategory: PCI/46
    ------------------------------------------------------------------------------

    alert2PCIDeviceConfigurationInformation TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "PCI device configuration information."
        --#TYPE       "Configuration: PCI Device Information"
        --#SEVERITY   INFORMATIONAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      OPERATIONAL
        --#STATUS     MANDATORY
        ::= 10611

    ------------------------------------------------------------------------------
    -- Chassis Alerts 2: Configuration: Software Configuration Traps
    --
    -- Category: Configuration/5
    -- Subcategory: SWC/36
    ------------------------------------------------------------------------------

    alert2SWCConfigurationWarning TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration warning."
        --#TYPE       "Configuration: Software Configuration Warning"
        --#SEVERITY   MINOR
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Status Events"
        --#STATE      DEGRADED
        --#STATUS     MANDATORY
        ::= 10530

    alert2SWCConfigurationFailure TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Software configuration failure."
        --#TYPE       "Configuration: Software Configuration Failure"
        --#SEVERITY   CRITICAL
        --#SUMMARY    "Message ID: %s, Message: %s,"
        --#SUMMARY    "Device Status: %d, Device FQDD: %s,"
        --#SUMMARY    "Chassis Service Tag: %s, Chassis Name: %s,"
        --#SUMMARY    "Chassis Location: %s, Global Status: %d"
        --#ARGUMENTS  {0, 1, 3, 4, 7, 5, 6, 8}
        --#CATEGORY   "Error Events"
        --#STATE      DEGRADED
        --#STATUS     MANDATORY
        ::= 10529

    ------------------------------------------------------------------------------
    -- Chassis Alerts 2: Configuration: Test Traps
    --
    -- Category: Configuration/5
    -- Subcategory: TST/19
    ------------------------------------------------------------------------------

    alert2CMCTestTrap TRAP-TYPE
        ENTERPRISE  drsCMCAlert2Group
        VARIABLES { drsCA2MessageID,
                    drsCA2Message,
                    drsCA2MessageArgs,
                    drsCA2AlertStatus,
                    drsCA2FQDD,
                    drsProductChassisName,
                    drsProductChassisLocation,
                    drsChassisServiceTag,
                    drsGlobalCurrStatus }
        DESCRIPTION
            "Test trap generated by CMC in response to a user request."
        --#TYPE       "Configuration: CMC Test Trap"
        --#SEVERITY   INFORMATIONAL
        --#SUMMARY    "%s"
        --#ARGUMENTS  {1}
        --#CATEGORY   "Status Events"
        --#STATE      OPERATIONAL
        --#STATUS     MANDATORY
        ::= 10395

	-------------------------------------------------------------------------------
    -- group: Legacy Alerts
	-------------------------------------------------------------------------------

        drsAlertSystem         OBJECT-TYPE
            SYNTAX             OCTET STRING (SIZE (0..255))
            ACCESS             read-only
            STATUS             mandatory
            DESCRIPTION
            "5000.0010.0001 Name of the system generating the alert."
            --DEFAULT get-function-async    get_%n_async
            --DEFAULT next-function-async   std_next_async
            ::= { drsAlertVariables 1 }

        drsAlertTableIndexOID  OBJECT-TYPE
            SYNTAX             OBJECT IDENTIFIER
            ACCESS             read-only
            STATUS             mandatory
            DESCRIPTION
            "5000.0010.0002 0.0"
            --DEFAULT get-function-async    get_OID_null_async
            --DEFAULT next-function-async   std_next_async
            ::= { drsAlertVariables 2 }

        drsAlertMessage        OBJECT-TYPE
            SYNTAX             OCTET STRING (SIZE (0..1024))
            ACCESS             read-only
            STATUS             mandatory
            DESCRIPTION
            "5000.0010.0003 Message describing the alert."
            --DEFAULT get-function-async    get_string_null_async
            --DEFAULT next-function-async   std_next_async
            ::= { drsAlertVariables 3 }

        drsAlertCurrentStatus  OBJECT-TYPE
            SYNTAX             DellStatus
            ACCESS             read-only
            STATUS             mandatory
            DESCRIPTION
            "5000.0010.0004 Current status of object causing the alert."
            --DEFAULT get-function-async    get_dellstatus_unknow_async
            --DEFAULT next-function-async   std_next_async
            ::= { drsAlertVariables 4 }

        drsAlertPreviousStatus OBJECT-TYPE
            SYNTAX             DellStatus
            ACCESS             read-only
            STATUS             mandatory
            DESCRIPTION
            "5000.0010.0005 Previous status of object causing the alert."
            --DEFAULT get-function-async    get_dellstatus_unknow_async
            --DEFAULT next-function-async   std_next_async
            ::= { drsAlertVariables 5 }

        drsAlertData           OBJECT-TYPE
            SYNTAX             OCTET STRING (SIZE (0..1024))
            ACCESS             read-only
            STATUS             mandatory
            DESCRIPTION
            "5000.0010.0006 Alert data."
            --DEFAULT get-function-async    get_string_null_async
            --DEFAULT next-function-async   std_next_async
            ::= { drsAlertVariables 6 }

        alertDrscTestTrapEvent      TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC generated a test trap event in response to a user request."
        --#TYPE "Dell RAC Test TRAP Event"
        --#SUMMARY "%s"
        --#ARGUMENTS {2}
        --#SEVERITY INFORMATIONAL
        --#CATEGORY Status Events
        ::= 1001
    
        alertDrscAuthError          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Authentication Failures during a time period have Exceeded a Threshold."
        --#TYPE "Dell RAC Authentication Error"
        --#SUMMARY "%s"
        --#ARGUMENTS {2}
        --#SEVERITY MINOR
        --#CATEGORY Error Events
        ::= 1002

        alertDrscLostESM          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC cannot communicate with the baseboard management controller (ESM)."
        --#TYPE "Dell RAC Lost Communication with ESM"
        --#SUMMARY "%s"
        --#ARGUMENTS {2}
        --#SEVERITY MINOR
        --#CATEGORY Error Events
        ::= 1003

        alertDrscFoundESM          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC is communicating normally with the baseboard management controller (ESM)."
        --#TYPE "Dell RAC Communication with ESM is OK"
        --#SUMMARY "%s"
        --#ARGUMENTS {2}
        --#SEVERITY INFORMATIONAL
        --#CATEGORY Error Events
        ::= 1004

        alertDrscPowerOff          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a System power state change to powered-off."
        --#TYPE "Dell RAC Detected System Powered-Off"
        --#SUMMARY "%s"
        --#ARGUMENTS {2}
        --#SEVERITY CRITICAL
        --#CATEGORY Error Events
        ::= 1005

        alertDrscPowerOn          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a system power state change to powered-on."
        --#TYPE "Dell RAC Detected System Powered-On"
        --#SUMMARY "%s"
        --#ARGUMENTS {2}
        --#SEVERITY INFORMATIONAL
        --#CATEGORY Error Events
        ::= 1006

        alertDrscWatchdogExpired          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the system watchdog has expired indicating a system hang."
        --#TYPE "Dell RAC Detected Watchdog Expired"
        --#SUMMARY "%s"
        --#ARGUMENTS {2}
        --#SEVERITY CRITICAL
        --#CATEGORY Error Events
        ::= 1007

        alertDrscBattLow          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Battery charge is below 25% indicating that the battery may only be able to power the DRSC for 8-10 minutes."
        --#TYPE "Dell RAC Battery Charge Low"
        --#SUMMARY "%s"
        --#ARGUMENTS {2}
        --#SEVERITY MINOR
        --#CATEGORY Error Events
        ::= 1008

        alertDrscTempNormal          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Temperature probe has retured to a normal value."
        --#TYPE "Dell RAC Temperature Normal"
        --#SUMMARY "%s"
        --#ARGUMENTS {2}
        --#SEVERITY INFORMATIONAL
        --#CATEGORY Error Events
        ::= 1009

        alertDrscTempWarning          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Temperature probe has detected a Warning value."
        --#TYPE "Dell RAC Temperature Warning"
        --#SUMMARY "%s"
        --#ARGUMENTS {2}
        --#SEVERITY MINOR
        --#CATEGORY Error Events
        ::= 1010

        alertDrscTempCritical          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC Temperature probe has detected a failure (or critical) value."
        --#TYPE "Dell RAC Temperature Failure"
        --#SUMMARY "%s"
        --#ARGUMENTS {2}
        --#SEVERITY CRITICAL
        --#CATEGORY Error Events
        ::= 1011

        alertDrscVoltNormal          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC voltage has returned to a normal value."
        --#TYPE "Dell RAC Voltage Normal"
        --#SUMMARY "%s"
        --#ARGUMENTS {2}
        --#SEVERITY INFORMATIONAL
        --#CATEGORY Error Events
        ::= 1012

        alertDrscVoltWarning          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC voltage probe has detected a warning value."
        --#TYPE "Dell RAC Battery Warning"
        --#SUMMARY "%s"
        --#ARGUMENTS {2}
        --#SEVERITY MINOR
        --#CATEGORY Error Events
        ::= 1013

        alertDrscVoltCritical          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC voltage probe has detected a failure (or critical) value."
        --#TYPE "Dell RAC Voltage Failure"
        --#SUMMARY "%s"
        --#ARGUMENTS {2}
        --#SEVERITY CRITICAL
        --#CATEGORY Error Events
        ::= 1014

        alertDrscSELWarning          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a new event in the System Event Log with Severity: Warning."
        --#TYPE "Dell RAC System Event Log Warning"
        --#SUMMARY "%s"
        --#ARGUMENTS {2}
        --#SEVERITY MAJOR
        --#CATEGORY Error Events
        ::= 1015

        alertDrscSELCritical          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a new event in the System Event Log with Severity: Critical."
        --#TYPE "Dell RAC System Event Log Critical"
        --#SUMMARY "%s"
        --#ARGUMENTS {2}
        --#SEVERITY CRITICAL
        --#CATEGORY Error Events
        ::= 1016

        alertDrscSEL80percentFull          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the System Event Log is 80% full."
        --#TYPE "Dell System Event Log 80% Full Warning"
        --#SUMMARY "%s"
        --#ARGUMENTS {2}
        --#SEVERITY MAJOR
        --#CATEGORY Status Events
        ::= 1017

        alertDrscSEL90percentFull          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the System Event Log is 90% full."
        --#TYPE " Dell System Event Log 90% Full Warning "
        --#SUMMARY "%s"
        --#ARGUMENTS {2}
        --#SEVERITY MAJOR
        --#CATEGORY Status Events
        ::= 1018

        alertDrscSEL100percentFull          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected that the System Event Log is 100% full."
        --#TYPE " Dell System Event Log 100% Full Warning "
        --#SUMMARY "%s"
        --#ARGUMENTS {2}
        --#SEVERITY MAJOR
        --#CATEGORY Status Events
        ::= 1019

        alertDrscSELNormal          TRAP-TYPE
        ENTERPRISE  drsOutofBandGroup
        VARIABLES { drsAlertSystem,
                    drsAlertTableIndexOID,
                    drsAlertMessage,
                    drsAlertCurrentStatus,
                    drsAlertPreviousStatus,
                    drsAlertData }
        DESCRIPTION
        "The RAC has detected a new event in the System Event Log with Severity: Normal."
        --#TYPE "Dell RAC System Event Log Normal"
        --#SUMMARY "%s"
        --#ARGUMENTS {2}
        --#SEVERITY INFORMATIONAL
        --#CATEGORY Error Events
        ::= 1020
END
