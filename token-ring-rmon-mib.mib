TOKEN-RING-RMON-MIB DEFINITIONS ::= BEGIN

IMPORTS
    MODULE-IDENTITY, OBJECT-TYPE,
    Counter32, Integer32                   FROM SNMPv2-SMI
    TimeInterval, TimeStamp, MacAddress    FROM SNMPv2-TC
    MODULE-COMPLIANCE, OBJECT-GROUP        FROM SNMPv2-CONF
    InterfaceIndex                         FROM IF-MIB
    OwnerString, EntryStatus,
    rmon, statistics, history,
    rmonCompliances, rmonGroups            FROM RMON-MIB;


--  Token Ring Remote Network Monitoring MIB

tokenRing MODULE-IDENTITY
    LAST-UPDATED "200103021500Z"  -- March 2, 2001
    ORGANIZATION "IETF RMON MIB Working Group"
    CONTACT-INFO
        "Steve Waldbusser

        Phone: +1-650-948-6500
        Fax:   +1-650-745-0671
        Email: waldbusser@nextbeacon.com

        Andy Bierman
        WG Chair
        abierman@cisco.com

        RMONMIB WG Mailing List
        rmonmib@ietf.org
        http://www.ietf.org/mailman/listinfo/rmonmib"
    DESCRIPTION
        "Remote network monitoring devices, often called
        monitors or probes, are instruments that exist for
        the purpose of managing a network. This MIB defines
        objects for managing remote network monitoring devices."

    REVISION "200103021500Z"    -- March 2, 2001
    DESCRIPTION
        "Reformatted into SMIv2 format.

        This version published as RFC XXXX."

    REVISION "9309010000Z"    -- 1 September, 1993
    DESCRIPTION
        "The original version of this MIB, published as RFC1513."
    ::= { rmon 10 }

-- The Token Ring Mac-Layer Statistics Group
--
-- Implementation of this group is optional
-- Consult the MODULE-COMPLIANCE macro for the authoritative
-- conformance information for this MIB.

tokenRingMLStatsTable OBJECT-TYPE
    SYNTAX     SEQUENCE OF TokenRingMLStatsEntry
    MAX-ACCESS not-accessible
    STATUS     current
    DESCRIPTION
            "A list of Mac-Layer Token Ring statistics
            entries."
    ::= { statistics 2 }

tokenRingMLStatsEntry OBJECT-TYPE
    SYNTAX     TokenRingMLStatsEntry
    MAX-ACCESS not-accessible
    STATUS     current
    DESCRIPTION
            "A collection of Mac-Layer statistics kept for a
            particular Token Ring interface."
    INDEX { tokenRingMLStatsIndex }
    ::= { tokenRingMLStatsTable 1 }

-- As an example, an instance of the tokenRingMLStatsMacOctets object
-- might be named tokenRingMLStatsMacOctets.1

TokenRingMLStatsEntry ::= SEQUENCE {
    tokenRingMLStatsIndex                     Integer32,
    tokenRingMLStatsDataSource                OBJECT IDENTIFIER,
    tokenRingMLStatsDropEvents                Counter32,
    tokenRingMLStatsMacOctets                 Counter32,
    tokenRingMLStatsMacPkts                   Counter32,
    tokenRingMLStatsRingPurgeEvents           Counter32,
    tokenRingMLStatsRingPurgePkts             Counter32,
    tokenRingMLStatsBeaconEvents              Counter32,
    tokenRingMLStatsBeaconTime                TimeInterval,
    tokenRingMLStatsBeaconPkts                Counter32,
    tokenRingMLStatsClaimTokenEvents          Counter32,
    tokenRingMLStatsClaimTokenPkts            Counter32,
    tokenRingMLStatsNAUNChanges               Counter32,
    tokenRingMLStatsLineErrors                Counter32,
    tokenRingMLStatsInternalErrors            Counter32,
    tokenRingMLStatsBurstErrors               Counter32,
    tokenRingMLStatsACErrors                  Counter32,
    tokenRingMLStatsAbortErrors               Counter32,
    tokenRingMLStatsLostFrameErrors           Counter32,
    tokenRingMLStatsCongestionErrors          Counter32,
    tokenRingMLStatsFrameCopiedErrors         Counter32,
    tokenRingMLStatsFrequencyErrors           Counter32,
    tokenRingMLStatsTokenErrors               Counter32,
    tokenRingMLStatsSoftErrorReports          Counter32,
    tokenRingMLStatsRingPollEvents            Counter32,
    tokenRingMLStatsOwner                     OwnerString,
    tokenRingMLStatsStatus                    EntryStatus
}

tokenRingMLStatsIndex OBJECT-TYPE
    SYNTAX     Integer32 (1..65535)
    MAX-ACCESS read-only
    STATUS     current
    DESCRIPTION
            "The value of this object uniquely identifies this
            tokenRingMLStats entry."
    ::= { tokenRingMLStatsEntry 1 }

tokenRingMLStatsDataSource OBJECT-TYPE
    SYNTAX     OBJECT IDENTIFIER
    MAX-ACCESS read-write
    STATUS     current
    DESCRIPTION
            "This object identifies the source of the data
            that this tokenRingMLStats entry is configured to
            analyze.  This source can be any tokenRing
            interface on this device.  In order to identify a
            particular interface, this object shall identify
            the instance of the ifIndex object, defined in the
            IF-MIB [17], for the desired interface.  For
            example, if an entry were to receive data from
            interface #1, this object would be set to
            ifIndex.1.

            The statistics in this group reflect all error
            reports on the local network segment attached to
            the identified interface.

            This object may not be modified if the associated
            tokenRingMLStatsStatus object is equal to
            valid(1)."
    ::= { tokenRingMLStatsEntry 2 }

tokenRingMLStatsDropEvents OBJECT-TYPE
    SYNTAX     Counter32
    MAX-ACCESS read-only
    STATUS     current
    DESCRIPTION
            "The total number of events in which packets were
            dropped by the probe due to lack of resources.
            Note that this number is not necessarily the
            number of packets dropped; it is just the number
            of times this condition has been detected.  This
            value is the same as the corresponding
            tokenRingPStatsDropEvents."
    ::= { tokenRingMLStatsEntry 3 }

tokenRingMLStatsMacOctets OBJECT-TYPE
    SYNTAX     Counter32
    MAX-ACCESS read-only
    STATUS     current
    DESCRIPTION
            "The total number of octets of data in MAC packets
            (excluding those that were not good frames)
            received on the network (excluding framing bits
            but including FCS octets)."
    ::= { tokenRingMLStatsEntry 4 }

tokenRingMLStatsMacPkts OBJECT-TYPE
    SYNTAX     Counter32
    MAX-ACCESS read-only
    STATUS     current
    DESCRIPTION
            "The total number of MAC packets (excluding
            packets that were not good frames) received."
    ::= { tokenRingMLStatsEntry 5 }

tokenRingMLStatsRingPurgeEvents OBJECT-TYPE
    SYNTAX     Counter32
    MAX-ACCESS read-only
    STATUS     current
    DESCRIPTION
            "The total number of times that the ring enters
            the ring purge state from normal ring state.  The
            ring purge state that comes in response to the
            claim token or beacon state is not counted."
    ::= { tokenRingMLStatsEntry 6 }

tokenRingMLStatsRingPurgePkts OBJECT-TYPE
    SYNTAX     Counter32
    MAX-ACCESS read-only
    STATUS     current
    DESCRIPTION
            "The total number of ring purge MAC packets
            detected by probe."
    ::= { tokenRingMLStatsEntry 7 }

tokenRingMLStatsBeaconEvents OBJECT-TYPE
    SYNTAX     Counter32
    MAX-ACCESS read-only
    STATUS     current
    DESCRIPTION
            "The total number of times that the ring enters a
            beaconing state (beaconFrameStreamingState,
            beaconBitStreamingState,
            beaconSetRecoveryModeState, or
            beaconRingSignalLossState) from a non-beaconing
            state.  Note that a change of the source address
            of the beacon packet does not constitute a new
            beacon event."
    ::= { tokenRingMLStatsEntry 8 }

tokenRingMLStatsBeaconTime OBJECT-TYPE
    SYNTAX     TimeInterval
    MAX-ACCESS read-only
    STATUS     current
    DESCRIPTION
            "The total amount of time that the ring has been
            in the beaconing state."
    ::= { tokenRingMLStatsEntry 9 }

tokenRingMLStatsBeaconPkts OBJECT-TYPE
    SYNTAX     Counter32
    MAX-ACCESS read-only
    STATUS     current
    DESCRIPTION
            "The total number of beacon MAC packets detected
            by the probe."
    ::= { tokenRingMLStatsEntry 10 }

tokenRingMLStatsClaimTokenEvents OBJECT-TYPE
    SYNTAX     Counter32
    MAX-ACCESS read-only
    STATUS     current
    DESCRIPTION
            "The total number of times that the ring enters
            the claim token state from normal ring state or
            ring purge state.  The claim token state that
            comes in response to a beacon state is not
            counted."
    ::= { tokenRingMLStatsEntry 11 }

tokenRingMLStatsClaimTokenPkts OBJECT-TYPE
    SYNTAX     Counter32
    MAX-ACCESS read-only
    STATUS     current
    DESCRIPTION
            "The total number of claim token MAC packets
            detected by the probe."
    ::= { tokenRingMLStatsEntry 12 }

tokenRingMLStatsNAUNChanges OBJECT-TYPE
    SYNTAX     Counter32
    MAX-ACCESS read-only
    STATUS     current
    DESCRIPTION
            "The total number of NAUN changes detected by the
            probe."
    ::= { tokenRingMLStatsEntry 13 }

tokenRingMLStatsLineErrors OBJECT-TYPE
    SYNTAX     Counter32
    MAX-ACCESS read-only
    STATUS     current
    DESCRIPTION
            "The total number of line errors reported in error
            reporting packets detected by the probe."
    ::= { tokenRingMLStatsEntry 14 }

tokenRingMLStatsInternalErrors OBJECT-TYPE
    SYNTAX     Counter32
    MAX-ACCESS read-only
    STATUS     current
    DESCRIPTION
            "The total number of adapter internal errors
            reported in error reporting packets detected by
            the probe."
    ::= { tokenRingMLStatsEntry 15 }

tokenRingMLStatsBurstErrors OBJECT-TYPE
    SYNTAX     Counter32
    MAX-ACCESS read-only
    STATUS     current
    DESCRIPTION
            "The total number of burst errors reported in
            error reporting packets detected by the probe."
    ::= { tokenRingMLStatsEntry 16 }

tokenRingMLStatsACErrors OBJECT-TYPE
    SYNTAX     Counter32
    MAX-ACCESS read-only
    STATUS     current
    DESCRIPTION
            "The total number of AC (Address Copied)  errors
            reported in error reporting packets detected by
            the probe."
    ::= { tokenRingMLStatsEntry 17 }

tokenRingMLStatsAbortErrors OBJECT-TYPE
    SYNTAX     Counter32
    MAX-ACCESS read-only
    STATUS     current
    DESCRIPTION
            "The total number of abort delimiters reported in
            error reporting packets detected by the probe."
    ::= { tokenRingMLStatsEntry 18 }

tokenRingMLStatsLostFrameErrors OBJECT-TYPE
    SYNTAX     Counter32
    MAX-ACCESS read-only
    STATUS     current
    DESCRIPTION
            "The total number of lost frame errors reported in
            error reporting packets detected by the probe."
    ::= { tokenRingMLStatsEntry 19 }

tokenRingMLStatsCongestionErrors OBJECT-TYPE
    SYNTAX     Counter32
    MAX-ACCESS read-only
    STATUS     current
    DESCRIPTION
            "The total number of receive congestion errors
            reported in error reporting packets detected by
            the probe."
    ::= { tokenRingMLStatsEntry 20 }

tokenRingMLStatsFrameCopiedErrors OBJECT-TYPE
    SYNTAX     Counter32
    MAX-ACCESS read-only
    STATUS     current
    DESCRIPTION
            "The total number of frame copied errors reported
            in error reporting packets detected by the probe."
    ::= { tokenRingMLStatsEntry 21 }

tokenRingMLStatsFrequencyErrors OBJECT-TYPE
    SYNTAX     Counter32
    MAX-ACCESS read-only
    STATUS     current
    DESCRIPTION
            "The total number of frequency errors reported in
            error reporting packets detected by the probe."
    ::= { tokenRingMLStatsEntry 22 }

tokenRingMLStatsTokenErrors OBJECT-TYPE
    SYNTAX     Counter32
    MAX-ACCESS read-only
    STATUS     current
    DESCRIPTION
            "The total number of token errors reported in
            error reporting packets detected by the probe."
    ::= { tokenRingMLStatsEntry 23 }

tokenRingMLStatsSoftErrorReports OBJECT-TYPE
    SYNTAX     Counter32
    MAX-ACCESS read-only
    STATUS     current
    DESCRIPTION
            "The total number of soft error report frames
            detected by the probe."
    ::= { tokenRingMLStatsEntry 24 }

tokenRingMLStatsRingPollEvents OBJECT-TYPE
    SYNTAX     Counter32
    MAX-ACCESS read-only
    STATUS     current
    DESCRIPTION
            "The total number of ring poll events detected by
            the probe (i.e. the number of ring polls initiated
            by the active monitor that were detected)."
    ::= { tokenRingMLStatsEntry 25 }

tokenRingMLStatsOwner OBJECT-TYPE
    SYNTAX     OwnerString
    MAX-ACCESS read-write
    STATUS     current
    DESCRIPTION
            "The entity that configured this entry and is
            therefore using the resources assigned to it."
    ::= { tokenRingMLStatsEntry 26 }

tokenRingMLStatsStatus OBJECT-TYPE
    SYNTAX     EntryStatus
    MAX-ACCESS read-write
    STATUS     current
    DESCRIPTION
            "The status of this tokenRingMLStats entry."
    ::= { tokenRingMLStatsEntry 27 }

-- The Token Ring Promiscuous Statistics Group
--
-- Implementation of this group is optional
-- Consult the MODULE-COMPLIANCE macro for the authoritative
-- conformance information for this MIB.

tokenRingPStatsTable OBJECT-TYPE
    SYNTAX     SEQUENCE OF TokenRingPStatsEntry
    MAX-ACCESS not-accessible
    STATUS     current
    DESCRIPTION
            "A list of promiscuous Token Ring statistics
            entries."
    ::= { statistics 3 }

tokenRingPStatsEntry OBJECT-TYPE
    SYNTAX     TokenRingPStatsEntry
    MAX-ACCESS not-accessible
    STATUS     current
    DESCRIPTION
            "A collection of promiscuous statistics kept for
            non-MAC packets on a particular Token Ring
            interface."
    INDEX { tokenRingPStatsIndex }
    ::= { tokenRingPStatsTable 1 }

-- As an example, an instance of the tokenRingPStatsDataOctets object
-- might be named tokenRingPStatsDataOctets.1

TokenRingPStatsEntry ::= SEQUENCE {
    tokenRingPStatsIndex                          Integer32,
    tokenRingPStatsDataSource                     OBJECT IDENTIFIER,
    tokenRingPStatsDropEvents                     Counter32,
    tokenRingPStatsDataOctets                     Counter32,
    tokenRingPStatsDataPkts                       Counter32,
    tokenRingPStatsDataBroadcastPkts              Counter32,
    tokenRingPStatsDataMulticastPkts              Counter32,
    tokenRingPStatsDataPkts18to63Octets           Counter32,
    tokenRingPStatsDataPkts64to127Octets          Counter32,
    tokenRingPStatsDataPkts128to255Octets         Counter32,
    tokenRingPStatsDataPkts256to511Octets         Counter32,
    tokenRingPStatsDataPkts512to1023Octets        Counter32,
    tokenRingPStatsDataPkts1024to2047Octets       Counter32,
    tokenRingPStatsDataPkts2048to4095Octets       Counter32,
    tokenRingPStatsDataPkts4096to8191Octets       Counter32,
    tokenRingPStatsDataPkts8192to18000Octets      Counter32,
    tokenRingPStatsDataPktsGreaterThan18000Octets Counter32,
    tokenRingPStatsOwner                          OwnerString,
    tokenRingPStatsStatus                         EntryStatus
}

tokenRingPStatsIndex OBJECT-TYPE
    SYNTAX     Integer32 (1..65535)
    MAX-ACCESS read-only
    STATUS     current
    DESCRIPTION
            "The value of this object uniquely identifies this
            tokenRingPStats entry."
    ::= { tokenRingPStatsEntry 1 }

tokenRingPStatsDataSource OBJECT-TYPE
    SYNTAX     OBJECT IDENTIFIER
    MAX-ACCESS read-write
    STATUS     current
    DESCRIPTION
            "This object identifies the source of the data
            that this tokenRingPStats entry is configured to
            analyze.  This source can be any tokenRing
            interface on this device.  In order to identify a
            particular interface, this object shall identify
            the instance of the ifIndex object, defined in IF-
            MIB [17], for the desired interface.  For example,
            if an entry were to receive data from interface
            #1, this object would be set to ifIndex.1.

            The statistics in this group reflect all non-MAC
            packets on the local network segment attached to
            the identified interface.

            This object may not be modified if the associated
            tokenRingPStatsStatus object is equal to
            valid(1)."
    ::= { tokenRingPStatsEntry 2 }

tokenRingPStatsDropEvents OBJECT-TYPE
    SYNTAX     Counter32
    MAX-ACCESS read-only
    STATUS     current
    DESCRIPTION
            "The total number of events in which packets were
            dropped by the probe due to lack of resources.
            Note that this number is not necessarily the
            number of packets dropped; it is just the number
            of times this condition has been detected.  This
            value is the same as the corresponding
            tokenRingMLStatsDropEvents"
    ::= { tokenRingPStatsEntry 3 }

tokenRingPStatsDataOctets OBJECT-TYPE
    SYNTAX     Counter32
    MAX-ACCESS read-only
    STATUS     current
    DESCRIPTION
            "The total number of octets of data in good frames
            received on the network (excluding framing bits
            but including FCS octets) in non-MAC packets."
    ::= { tokenRingPStatsEntry 4 }

tokenRingPStatsDataPkts OBJECT-TYPE
    SYNTAX     Counter32
    MAX-ACCESS read-only
    STATUS     current
    DESCRIPTION
            "The total number of non-MAC packets in good
            frames received."
    ::= { tokenRingPStatsEntry 5 }

tokenRingPStatsDataBroadcastPkts OBJECT-TYPE
    SYNTAX     Counter32
    MAX-ACCESS read-only
    STATUS     current
    DESCRIPTION
            "The total number of non-MAC good frames received
            that were directed to an LLC broadcast address
            (0xFFFFFFFFFFFF or 0xC000FFFFFFFF)."
    ::= { tokenRingPStatsEntry 6 }

tokenRingPStatsDataMulticastPkts OBJECT-TYPE
    SYNTAX     Counter32
    MAX-ACCESS read-only
    STATUS     current
    DESCRIPTION
            "The total number of non-MAC good frames received
            that were directed to a local or global multicast
            or functional address.  Note that this number does
            not include packets directed to the broadcast
            address."
    ::= { tokenRingPStatsEntry 7 }

tokenRingPStatsDataPkts18to63Octets OBJECT-TYPE
    SYNTAX     Counter32
    MAX-ACCESS read-only
    STATUS     current
    DESCRIPTION
            "The total number of non-MAC good frames received
            that were between 18 and 63 octets in length
            inclusive, excluding framing bits but including
            FCS octets."
    ::= { tokenRingPStatsEntry 8 }

tokenRingPStatsDataPkts64to127Octets OBJECT-TYPE
    SYNTAX     Counter32
    MAX-ACCESS read-only
    STATUS     current
    DESCRIPTION
            "The total number of non-MAC good frames received
            that were between 64 and 127 octets in length
            inclusive, excluding framing bits but including
            FCS octets."
    ::= { tokenRingPStatsEntry 9 }

tokenRingPStatsDataPkts128to255Octets OBJECT-TYPE
    SYNTAX     Counter32
    MAX-ACCESS read-only
    STATUS     current
    DESCRIPTION
            "The total number of non-MAC good frames received
            that were between 128 and 255 octets in length
            inclusive, excluding framing bits but including
            FCS octets."
    ::= { tokenRingPStatsEntry 10 }

tokenRingPStatsDataPkts256to511Octets OBJECT-TYPE
    SYNTAX     Counter32
    MAX-ACCESS read-only
    STATUS     current
    DESCRIPTION
            "The total number of non-MAC good frames received
            that were between 256 and 511 octets in length
            inclusive, excluding framing bits but including
            FCS octets."
    ::= { tokenRingPStatsEntry 11 }

tokenRingPStatsDataPkts512to1023Octets OBJECT-TYPE
    SYNTAX     Counter32
    MAX-ACCESS read-only
    STATUS     current
    DESCRIPTION
            "The total number of non-MAC good frames received
            that were between 512 and 1023 octets in length
            inclusive, excluding framing bits but including
            FCS octets."
    ::= { tokenRingPStatsEntry 12 }

tokenRingPStatsDataPkts1024to2047Octets OBJECT-TYPE
    SYNTAX     Counter32
    MAX-ACCESS read-only
    STATUS     current
    DESCRIPTION
            "The total number of non-MAC good frames received
            that were between 1024 and 2047 octets in length
            inclusive, excluding framing bits but including
            FCS octets."
    ::= { tokenRingPStatsEntry 13 }

tokenRingPStatsDataPkts2048to4095Octets OBJECT-TYPE
    SYNTAX     Counter32
    MAX-ACCESS read-only
    STATUS     current
    DESCRIPTION
            "The total number of non-MAC good frames received
            that were between 2048 and 4095 octets in length
            inclusive, excluding framing bits but including
            FCS octets."
    ::= { tokenRingPStatsEntry 14 }

tokenRingPStatsDataPkts4096to8191Octets OBJECT-TYPE
    SYNTAX     Counter32
    MAX-ACCESS read-only
    STATUS     current
    DESCRIPTION
            "The total number of non-MAC good frames received
            that were between 4096 and 8191 octets in length
            inclusive, excluding framing bits but including
            FCS octets."
    ::= { tokenRingPStatsEntry 15 }

tokenRingPStatsDataPkts8192to18000Octets OBJECT-TYPE
    SYNTAX     Counter32
    MAX-ACCESS read-only
    STATUS     current
    DESCRIPTION
            "The total number of non-MAC good frames received
            that were between 8192 and 18000 octets in length
            inclusive, excluding framing bits but including
            FCS octets."
    ::= { tokenRingPStatsEntry 16 }

tokenRingPStatsDataPktsGreaterThan18000Octets OBJECT-TYPE
    SYNTAX     Counter32
    MAX-ACCESS read-only
    STATUS     current
    DESCRIPTION
            "The total number of non-MAC good frames received
            that were greater than 18000 octets in length,
            excluding framing bits but including FCS octets."
    ::= { tokenRingPStatsEntry 17 }

tokenRingPStatsOwner OBJECT-TYPE
    SYNTAX     OwnerString
    MAX-ACCESS read-write
    STATUS     current
    DESCRIPTION
            "The entity that configured this entry and is
            therefore using the resources assigned to it."
    ::= { tokenRingPStatsEntry 18 }

tokenRingPStatsStatus OBJECT-TYPE
    SYNTAX     EntryStatus
    MAX-ACCESS read-write
    STATUS     current
    DESCRIPTION
            "The status of this tokenRingPStats entry."
    ::= { tokenRingPStatsEntry 19 }

-- The Token Ring History Groups

-- When an entry in the historyControlTable is created that
-- identifies a token ring interface as its
-- historyControlDataSource, the probe shall create corresponding
-- entries in the tokenRingMLHistoryTable and/or the
-- tokenRingPHistoryTable, depending on which groups it supports.



-- The Token Ring Mac-Layer History Group
--
-- Implementation of this group is optional.
-- Implementation of this group requires implementation of the
-- historyControl group from RFC2819.
-- Consult the MODULE-COMPLIANCE macro for the authoritative
-- conformance information for this MIB.

tokenRingMLHistoryTable OBJECT-TYPE
    SYNTAX     SEQUENCE OF TokenRingMLHistoryEntry
    MAX-ACCESS not-accessible
    STATUS     current
    DESCRIPTION
            "A list of Mac-Layer Token Ring statistics
            entries."
    ::= { history 3 }

tokenRingMLHistoryEntry OBJECT-TYPE
    SYNTAX     TokenRingMLHistoryEntry
    MAX-ACCESS not-accessible
    STATUS     current
    DESCRIPTION
            "A collection of Mac-Layer statistics kept for a
            particular Token Ring interface."
    INDEX { tokenRingMLHistoryIndex,  tokenRingMLHistorySampleIndex }
    ::= { tokenRingMLHistoryTable 1 }

-- As an example, an instance of the tokenRingMLHistoryMacOctets
-- object might be named tokenRingMLHistoryMacOctets.1.27

TokenRingMLHistoryEntry ::= SEQUENCE {
    tokenRingMLHistoryIndex                     Integer32,
    tokenRingMLHistorySampleIndex               Integer32,
    tokenRingMLHistoryIntervalStart             TimeStamp,
    tokenRingMLHistoryDropEvents                Counter32,
    tokenRingMLHistoryMacOctets                 Counter32,
    tokenRingMLHistoryMacPkts                   Counter32,
    tokenRingMLHistoryRingPurgeEvents           Counter32,
    tokenRingMLHistoryRingPurgePkts             Counter32,
    tokenRingMLHistoryBeaconEvents              Counter32,
    tokenRingMLHistoryBeaconTime                TimeInterval,
    tokenRingMLHistoryBeaconPkts                Counter32,
    tokenRingMLHistoryClaimTokenEvents          Counter32,
    tokenRingMLHistoryClaimTokenPkts            Counter32,
    tokenRingMLHistoryNAUNChanges               Counter32,
    tokenRingMLHistoryLineErrors                Counter32,
    tokenRingMLHistoryInternalErrors            Counter32,
    tokenRingMLHistoryBurstErrors               Counter32,
    tokenRingMLHistoryACErrors                  Counter32,
    tokenRingMLHistoryAbortErrors               Counter32,
    tokenRingMLHistoryLostFrameErrors           Counter32,
    tokenRingMLHistoryCongestionErrors          Counter32,
    tokenRingMLHistoryFrameCopiedErrors         Counter32,
    tokenRingMLHistoryFrequencyErrors           Counter32,
    tokenRingMLHistoryTokenErrors               Counter32,
    tokenRingMLHistorySoftErrorReports          Counter32,
    tokenRingMLHistoryRingPollEvents            Counter32,
    tokenRingMLHistoryActiveStations            Integer32
}

tokenRingMLHistoryIndex OBJECT-TYPE
    SYNTAX     Integer32 (1..65535)
    MAX-ACCESS read-only
    STATUS     current
    DESCRIPTION
            "The history of which this entry is a part.  The
            history identified by a particular value of this
            index is the same history as identified by the
            same value of historyControlIndex."
    ::= { tokenRingMLHistoryEntry 1 }

tokenRingMLHistorySampleIndex OBJECT-TYPE
    SYNTAX     Integer32 (1..2147483647)
    MAX-ACCESS read-only
    STATUS     current
    DESCRIPTION
            "An index that uniquely identifies the particular
            Mac-Layer sample this entry represents among all
            Mac-Layer samples associated with the same
            historyControlEntry.  This index starts at 1 and
            increases by one as each new sample is taken."
    ::= { tokenRingMLHistoryEntry 2 }

tokenRingMLHistoryIntervalStart OBJECT-TYPE
    SYNTAX     TimeStamp
    MAX-ACCESS read-only
    STATUS     current
    DESCRIPTION
            "The value of sysUpTime at the start of the
            interval over which this sample was measured.  If
            the probe keeps track of the time of day, it
            should start the first sample of the history at a
            time such that when the next hour of the day
            begins, a sample is started at that instant.  Note
            that following this rule may require the probe to
            delay collecting the first sample of the history,
            as each sample must be of the same interval.  Also
            note that the sample which is currently being
            collected is not accessible in this table until
            the end of its interval."
    ::= { tokenRingMLHistoryEntry 3 }

tokenRingMLHistoryDropEvents OBJECT-TYPE
    SYNTAX     Counter32
    MAX-ACCESS read-only
    STATUS     current
    DESCRIPTION
            "The total number of events in which packets were
            dropped by the probe due to lack of resources
            during this sampling interval.  Note that this
            number is not necessarily the number of packets
            dropped, it is just the number of times this
            condition has been detected."
    ::= { tokenRingMLHistoryEntry 4 }

tokenRingMLHistoryMacOctets OBJECT-TYPE
    SYNTAX     Counter32
    MAX-ACCESS read-only
    STATUS     current
    DESCRIPTION
            "The total number of octets of data in MAC packets
            (excluding those that were not good frames)
            received on the network during this sampling
            interval (excluding framing bits but including FCS
            octets)."
    ::= { tokenRingMLHistoryEntry 5 }

tokenRingMLHistoryMacPkts OBJECT-TYPE
    SYNTAX     Counter32
    MAX-ACCESS read-only
    STATUS     current
    DESCRIPTION
            "The total number of MAC packets (excluding those
            that were not good frames) received during this
            sampling interval."
    ::= { tokenRingMLHistoryEntry 6 }

tokenRingMLHistoryRingPurgeEvents OBJECT-TYPE
    SYNTAX     Counter32
    MAX-ACCESS read-only
    STATUS     current
    DESCRIPTION
            "The total number of times that the ring entered
            the ring purge state from normal ring state during
            this sampling interval.  The ring purge state that
            comes from the claim token or beacon state is not
            counted."
    ::= { tokenRingMLHistoryEntry 7 }

tokenRingMLHistoryRingPurgePkts OBJECT-TYPE
    SYNTAX     Counter32
    MAX-ACCESS read-only
    STATUS     current
    DESCRIPTION
            "The total number of Ring Purge MAC packets
            detected by the probe during this sampling
            interval."
    ::= { tokenRingMLHistoryEntry 8 }

tokenRingMLHistoryBeaconEvents OBJECT-TYPE
    SYNTAX     Counter32
    MAX-ACCESS read-only
    STATUS     current
    DESCRIPTION
            "The total number of times that the ring enters a
            beaconing state (beaconFrameStreamingState,
            beaconBitStreamingState,
            beaconSetRecoveryModeState, or
            beaconRingSignalLossState) during this sampling
            interval.  Note that a change of the source
            address of the beacon packet does not constitute a
            new beacon event."
    ::= { tokenRingMLHistoryEntry 9 }

tokenRingMLHistoryBeaconTime OBJECT-TYPE
    SYNTAX     TimeInterval
    MAX-ACCESS read-only
    STATUS     current
    DESCRIPTION
            "The amount of time that the ring has been in the
            beaconing state during this sampling interval."
    ::= { tokenRingMLHistoryEntry 10 }

tokenRingMLHistoryBeaconPkts OBJECT-TYPE
    SYNTAX     Counter32
    MAX-ACCESS read-only
    STATUS     current
    DESCRIPTION
            "The total number of beacon MAC packets detected
            by the probe during this sampling interval."
    ::= { tokenRingMLHistoryEntry 11 }

tokenRingMLHistoryClaimTokenEvents OBJECT-TYPE
    SYNTAX     Counter32
    MAX-ACCESS read-only
    STATUS     current
    DESCRIPTION
            "The total number of times that the ring enters
            the claim token state from normal ring state or
            ring purge state during this sampling interval.
            The claim token state that comes from the beacon
            state is not counted."
    ::= { tokenRingMLHistoryEntry 12 }

tokenRingMLHistoryClaimTokenPkts OBJECT-TYPE
    SYNTAX     Counter32
    MAX-ACCESS read-only
    STATUS     current
    DESCRIPTION
            "The total number of claim token MAC packets
            detected by the probe during this sampling
            interval."
    ::= { tokenRingMLHistoryEntry 13 }

tokenRingMLHistoryNAUNChanges OBJECT-TYPE
    SYNTAX     Counter32
    MAX-ACCESS read-only
    STATUS     current
    DESCRIPTION
            "The total number of NAUN changes detected by the
            probe during this sampling interval."
    ::= { tokenRingMLHistoryEntry 14 }

tokenRingMLHistoryLineErrors OBJECT-TYPE
    SYNTAX     Counter32
    MAX-ACCESS read-only
    STATUS     current
    DESCRIPTION
            "The total number of line errors reported in error
            reporting packets detected by the probe during
            this sampling interval."
    ::= { tokenRingMLHistoryEntry 15 }

tokenRingMLHistoryInternalErrors OBJECT-TYPE
    SYNTAX     Counter32
    MAX-ACCESS read-only
    STATUS     current
    DESCRIPTION
            "The total number of adapter internal errors
            reported in error reporting packets detected by
            the probe during this sampling interval."
    ::= { tokenRingMLHistoryEntry 16 }

tokenRingMLHistoryBurstErrors OBJECT-TYPE
    SYNTAX     Counter32
    MAX-ACCESS read-only
    STATUS     current
    DESCRIPTION
            "The total number of burst errors reported in
            error reporting packets detected by the probe
            during this sampling interval."
    ::= { tokenRingMLHistoryEntry 17 }

tokenRingMLHistoryACErrors OBJECT-TYPE
    SYNTAX     Counter32
    MAX-ACCESS read-only
    STATUS     current
    DESCRIPTION
            "The total number of AC (Address Copied) errors
            reported in error reporting packets detected by
            the probe during this sampling interval."
    ::= { tokenRingMLHistoryEntry 18 }

tokenRingMLHistoryAbortErrors OBJECT-TYPE
    SYNTAX     Counter32
    MAX-ACCESS read-only
    STATUS     current
    DESCRIPTION
            "The total number of abort delimiters reported in
            error reporting packets detected by the probe
            during this sampling interval."
    ::= { tokenRingMLHistoryEntry 19 }

tokenRingMLHistoryLostFrameErrors OBJECT-TYPE
    SYNTAX     Counter32
    MAX-ACCESS read-only
    STATUS     current
    DESCRIPTION
            "The total number of lost frame errors reported in
            error reporting packets detected by the probe
            during this sampling interval."
    ::= { tokenRingMLHistoryEntry 20 }

tokenRingMLHistoryCongestionErrors OBJECT-TYPE
    SYNTAX     Counter32
    MAX-ACCESS read-only
    STATUS     current
    DESCRIPTION
            "The total number of receive congestion errors
            reported in error reporting packets detected by
            the probe during this sampling interval."
    ::= { tokenRingMLHistoryEntry 21 }

tokenRingMLHistoryFrameCopiedErrors OBJECT-TYPE
    SYNTAX     Counter32
    MAX-ACCESS read-only
    STATUS     current
    DESCRIPTION
            "The total number of frame copied errors reported
            in error reporting packets detected by the probe
            during this sampling interval."
    ::= { tokenRingMLHistoryEntry 22 }

tokenRingMLHistoryFrequencyErrors OBJECT-TYPE
    SYNTAX     Counter32
    MAX-ACCESS read-only
    STATUS     current
    DESCRIPTION
            "The total number of frequency errors reported in
            error reporting packets detected by the probe
            during this sampling interval."
    ::= { tokenRingMLHistoryEntry 23 }

tokenRingMLHistoryTokenErrors OBJECT-TYPE
    SYNTAX     Counter32
    MAX-ACCESS read-only
    STATUS     current
    DESCRIPTION
            "The total number of token errors reported in
            error reporting packets detected by the probe
            during this sampling interval."
    ::= { tokenRingMLHistoryEntry 24 }

tokenRingMLHistorySoftErrorReports OBJECT-TYPE
    SYNTAX     Counter32
    MAX-ACCESS read-only
    STATUS     current
    DESCRIPTION
            "The total number of soft error report frames
            detected by the probe during this sampling
            interval."
    ::= { tokenRingMLHistoryEntry 25 }

tokenRingMLHistoryRingPollEvents OBJECT-TYPE
    SYNTAX     Counter32
    MAX-ACCESS read-only
    STATUS     current
    DESCRIPTION
            "The total number of ring poll events detected by
            the probe during this sampling interval."
    ::= { tokenRingMLHistoryEntry 26 }

tokenRingMLHistoryActiveStations OBJECT-TYPE
    SYNTAX     Integer32
    MAX-ACCESS read-only
    STATUS     current
    DESCRIPTION
            "The maximum number of active stations on the ring
            detected by the probe during this sampling
            interval."
    ::= { tokenRingMLHistoryEntry 27}

-- The Token Ring Promiscuous History Group
--
-- Implementation of this group is optional.
-- Implementation of this group requires the implementation of the
-- historyControl group from RFC2819.
-- Consult the MODULE-COMPLIANCE macro for the authoritative
-- conformance information for this MIB.

tokenRingPHistoryTable OBJECT-TYPE
    SYNTAX     SEQUENCE OF TokenRingPHistoryEntry
    MAX-ACCESS not-accessible
    STATUS     current
    DESCRIPTION
            "A list of promiscuous Token Ring statistics
            entries."
    ::= { history 4 }

tokenRingPHistoryEntry OBJECT-TYPE
    SYNTAX     TokenRingPHistoryEntry
    MAX-ACCESS not-accessible
    STATUS     current
    DESCRIPTION
            "A collection of promiscuous statistics kept for a
            particular Token Ring interface."
    INDEX { tokenRingPHistoryIndex, tokenRingPHistorySampleIndex }
    ::= { tokenRingPHistoryTable 1 }

-- As an example, an instance of the tokenRingPHistoryDataPkts object
-- might be named tokenRingPHistoryDataPkts.1.27

TokenRingPHistoryEntry ::= SEQUENCE {
    tokenRingPHistoryIndex                          Integer32,
    tokenRingPHistorySampleIndex                    Integer32,
    tokenRingPHistoryIntervalStart                  TimeStamp,
    tokenRingPHistoryDropEvents                     Counter32,
    tokenRingPHistoryDataOctets                     Counter32,
    tokenRingPHistoryDataPkts                       Counter32,
    tokenRingPHistoryDataBroadcastPkts              Counter32,
    tokenRingPHistoryDataMulticastPkts              Counter32,
    tokenRingPHistoryDataPkts18to63Octets           Counter32,
    tokenRingPHistoryDataPkts64to127Octets          Counter32,
    tokenRingPHistoryDataPkts128to255Octets         Counter32,
    tokenRingPHistoryDataPkts256to511Octets         Counter32,
    tokenRingPHistoryDataPkts512to1023Octets        Counter32,
    tokenRingPHistoryDataPkts1024to2047Octets       Counter32,
    tokenRingPHistoryDataPkts2048to4095Octets       Counter32,
    tokenRingPHistoryDataPkts4096to8191Octets       Counter32,
    tokenRingPHistoryDataPkts8192to18000Octets      Counter32,
    tokenRingPHistoryDataPktsGreaterThan18000Octets Counter32
}

tokenRingPHistoryIndex OBJECT-TYPE
    SYNTAX     Integer32 (1..65535)
    MAX-ACCESS read-only
    STATUS     current
    DESCRIPTION
            "The history of which this entry is a part.  The
            history identified by a particular value of this
            index is the same history as identified by the
            same value of historyControlIndex."
    ::= { tokenRingPHistoryEntry 1 }

tokenRingPHistorySampleIndex OBJECT-TYPE
    SYNTAX     Integer32 (1..2147483647)
    MAX-ACCESS read-only
    STATUS     current
    DESCRIPTION
            "An index that uniquely identifies the particular
            sample this entry represents among all samples
            associated with the same historyControlEntry.
            This index starts at 1 and increases by one as
            each new sample is taken."
    ::= { tokenRingPHistoryEntry 2 }

tokenRingPHistoryIntervalStart OBJECT-TYPE
    SYNTAX     TimeStamp
    MAX-ACCESS read-only
    STATUS     current
    DESCRIPTION
            "The value of sysUpTime at the start of the
            interval over which this sample was measured.  If
            the probe keeps track of the time of day, it
            should start the first sample of the history at a
            time such that when the next hour of the day
            begins, a sample is started at that instant.  Note
            that following this rule may require the probe to
            delay collecting the first sample of the history,
            as each sample must be of the same interval.  Also
            note that the sample which is currently being
            collected is not accessible in this table until
            the end of its interval."
    ::= { tokenRingPHistoryEntry 3 }

tokenRingPHistoryDropEvents OBJECT-TYPE
    SYNTAX     Counter32
    MAX-ACCESS read-only
    STATUS     current
    DESCRIPTION
            "The total number of events in which packets were
            dropped by the probe due to lack of resources
            during this sampling interval.  Note that this
            number is not necessarily the number of packets
            dropped, it is just the number of times this
            condition has been detected."
    ::= { tokenRingPHistoryEntry 4 }

tokenRingPHistoryDataOctets OBJECT-TYPE
    SYNTAX     Counter32
    MAX-ACCESS read-only
    STATUS     current
    DESCRIPTION
            "The total number of octets of data in good frames
            received on the network (excluding framing bits
            but including FCS octets) in non-MAC packets
            during this sampling interval."
    ::= { tokenRingPHistoryEntry 5 }

tokenRingPHistoryDataPkts OBJECT-TYPE
    SYNTAX     Counter32
    MAX-ACCESS read-only
    STATUS     current
    DESCRIPTION
            "The total number of non-MAC good frames received
            during this sampling interval."
    ::= { tokenRingPHistoryEntry 6 }

tokenRingPHistoryDataBroadcastPkts OBJECT-TYPE
    SYNTAX     Counter32
    MAX-ACCESS read-only
    STATUS     current
    DESCRIPTION
            "The total number of non-MAC good frames received
            during this sampling interval that were directed
            to an LLC broadcast address (0xFFFFFFFFFFFF or
            0xC000FFFFFFFF)."
    ::= { tokenRingPHistoryEntry 7 }

tokenRingPHistoryDataMulticastPkts OBJECT-TYPE
    SYNTAX     Counter32
    MAX-ACCESS read-only
    STATUS     current
    DESCRIPTION
            "The total number of non-MAC good frames received
            during this sampling interval that were directed
            to a local or global multicast or functional
            address.  Note that this number does not include
            packets directed to the broadcast address."
    ::= { tokenRingPHistoryEntry 8 }

tokenRingPHistoryDataPkts18to63Octets OBJECT-TYPE
    SYNTAX     Counter32
    MAX-ACCESS read-only
    STATUS     current
    DESCRIPTION
            "The total number of non-MAC good frames received
            during this sampling interval that were between 18
            and 63 octets in length inclusive, excluding
            framing bits but including FCS octets."
    ::= { tokenRingPHistoryEntry 9 }

tokenRingPHistoryDataPkts64to127Octets OBJECT-TYPE
    SYNTAX     Counter32
    MAX-ACCESS read-only
    STATUS     current
    DESCRIPTION
            "The total number of non-MAC good frames received
            during this sampling interval that were between 64
            and 127 octets in length inclusive, excluding
            framing bits but including FCS octets."
    ::= { tokenRingPHistoryEntry 10 }

tokenRingPHistoryDataPkts128to255Octets OBJECT-TYPE
    SYNTAX     Counter32
    MAX-ACCESS read-only
    STATUS     current
    DESCRIPTION
            "The total number of non-MAC good frames received
            during this sampling interval that were between
            128 and 255 octets in length inclusive, excluding
            framing bits but including FCS octets."
    ::= { tokenRingPHistoryEntry 11 }

tokenRingPHistoryDataPkts256to511Octets OBJECT-TYPE
    SYNTAX     Counter32
    MAX-ACCESS read-only
    STATUS     current
    DESCRIPTION
            "The total number of non-MAC good frames received
            during this sampling interval that were between
            256 and 511 octets in length inclusive, excluding
            framing bits but including FCS octets."
    ::= { tokenRingPHistoryEntry 12 }

tokenRingPHistoryDataPkts512to1023Octets OBJECT-TYPE
    SYNTAX     Counter32
    MAX-ACCESS read-only
    STATUS     current
    DESCRIPTION
            "The total number of non-MAC good frames received
            during this sampling interval that were between
            512 and 1023 octets in length inclusive, excluding
            framing bits but including FCS octets."
    ::= { tokenRingPHistoryEntry 13 }

tokenRingPHistoryDataPkts1024to2047Octets OBJECT-TYPE
    SYNTAX     Counter32
    MAX-ACCESS read-only
    STATUS     current
    DESCRIPTION
            "The total number of non-MAC good frames received
            during this sampling interval that were between
            1024 and 2047 octets in length inclusive,
            excluding framing bits but including FCS octets."
    ::= { tokenRingPHistoryEntry 14 }

tokenRingPHistoryDataPkts2048to4095Octets OBJECT-TYPE
    SYNTAX     Counter32
    MAX-ACCESS read-only
    STATUS     current
    DESCRIPTION
            "The total number of non-MAC good frames received
            during this sampling interval that were between
            2048 and 4095 octets in length inclusive,
            excluding framing bits but including FCS octets."
    ::= { tokenRingPHistoryEntry 15 }

tokenRingPHistoryDataPkts4096to8191Octets OBJECT-TYPE
    SYNTAX     Counter32
    MAX-ACCESS read-only
    STATUS     current
    DESCRIPTION
            "The total number of non-MAC good frames received
            during this sampling interval that were between
            4096 and 8191 octets in length inclusive,
            excluding framing bits but including FCS octets."
    ::= { tokenRingPHistoryEntry 16 }

tokenRingPHistoryDataPkts8192to18000Octets OBJECT-TYPE
    SYNTAX     Counter32
    MAX-ACCESS read-only
    STATUS     current
    DESCRIPTION
            "The total number of non-MAC good frames received
            during this sampling interval that were between
            8192 and 18000 octets in length inclusive,
            excluding framing bits but including FCS octets."
    ::= { tokenRingPHistoryEntry 17 }

tokenRingPHistoryDataPktsGreaterThan18000Octets OBJECT-TYPE
    SYNTAX     Counter32
    MAX-ACCESS read-only
    STATUS     current
    DESCRIPTION
            "The total number of non-MAC good frames received
            during this sampling interval that were greater
            than 18000 octets in length, excluding framing
            bits but including FCS octets."
    ::= { tokenRingPHistoryEntry 18 }

-- The Token Ring Ring Station Group
--
-- Implementation of this group is optional
-- Consult the MODULE-COMPLIANCE macro for the authoritative
-- conformance information for this MIB.
--
-- Although the ringStationTable stores entries only for those
-- stations physically attached to the local ring and the number of
-- stations attached to a ring is limited, a probe may still need to
-- free resources when resources grow tight.  In such a situation, it
-- is suggested that the probe free only inactive stations, and to
-- first free the stations that have been inactive for the longest
-- time.

ringStationControlTable OBJECT-TYPE
    SYNTAX     SEQUENCE OF RingStationControlEntry
    MAX-ACCESS not-accessible
    STATUS     current
    DESCRIPTION
            "A list of ringStation table control entries."
    ::= { tokenRing 1 }

ringStationControlEntry OBJECT-TYPE
    SYNTAX     RingStationControlEntry
    MAX-ACCESS not-accessible
    STATUS     current
    DESCRIPTION
            "A list of parameters that set up the discovery of
            stations on a particular interface and the
            collection of statistics about these stations."
    INDEX { ringStationControlIfIndex }
    ::= { ringStationControlTable 1 }

-- As an example, an instance of the ringStationControlIfIndex object
-- might be named ringStationControlIfIndex.1

RingStationControlEntry ::= SEQUENCE {
    ringStationControlIfIndex          InterfaceIndex,
    ringStationControlTableSize        Integer32,
    ringStationControlActiveStations   Integer32,
    ringStationControlRingState        INTEGER,
    ringStationControlBeaconSender     MacAddress,
    ringStationControlBeaconNAUN       MacAddress,
    ringStationControlActiveMonitor    MacAddress,
    ringStationControlOrderChanges     Counter32,
    ringStationControlOwner            OwnerString,
    ringStationControlStatus           EntryStatus
}

ringStationControlIfIndex OBJECT-TYPE
    SYNTAX     InterfaceIndex
    MAX-ACCESS read-only
    STATUS     current
    DESCRIPTION
            "The value of this object uniquely identifies the
            interface on this remote network monitoring device
            from which ringStation data is collected.  The
            interface identified by a particular value of this
            object is the same interface as identified by the
            same value of the ifIndex object, defined in IF-
            MIB [17]."
    ::= { ringStationControlEntry 1 }

ringStationControlTableSize OBJECT-TYPE
    SYNTAX     Integer32
    MAX-ACCESS read-only
    STATUS     current
    DESCRIPTION
            "The number of ringStationEntries in the
            ringStationTable associated with this
            ringStationControlEntry."
    ::= { ringStationControlEntry 2 }

ringStationControlActiveStations OBJECT-TYPE
    SYNTAX     Integer32
    MAX-ACCESS read-only
    STATUS     current
    DESCRIPTION
            "The number of active ringStationEntries in the
            ringStationTable associated with this
            ringStationControlEntry."
    ::= { ringStationControlEntry 3 }

ringStationControlRingState OBJECT-TYPE
    SYNTAX     INTEGER {
        normalOperation(1),
        ringPurgeState(2),
        claimTokenState(3),
        beaconFrameStreamingState(4),
        beaconBitStreamingState(5),
        beaconRingSignalLossState(6),
        beaconSetRecoveryModeState(7)
    }
    MAX-ACCESS read-only
    STATUS     current
    DESCRIPTION
            "The current status of this ring."
    ::= { ringStationControlEntry 4 }

ringStationControlBeaconSender OBJECT-TYPE
    SYNTAX     MacAddress
    MAX-ACCESS read-only
    STATUS     current
    DESCRIPTION
            "The address of the sender of the last beacon
            frame received by the probe on this ring.  If no
            beacon frames have been received, this object
            shall be equal to six octets of zero."
    ::= { ringStationControlEntry 5 }

ringStationControlBeaconNAUN OBJECT-TYPE
    SYNTAX     MacAddress
    MAX-ACCESS read-only
    STATUS     current
    DESCRIPTION
            "The address of the NAUN in the last beacon frame
            received by the probe on this ring.  If no beacon
            frames have been received, this object shall be
            equal to six octets of zero."
    ::= { ringStationControlEntry 6 }

ringStationControlActiveMonitor OBJECT-TYPE
    SYNTAX     MacAddress
    MAX-ACCESS read-only
    STATUS     current
    DESCRIPTION
            "The address of the Active Monitor on this
            segment.  If this address is unknown, this object
            shall be equal to six octets of zero."
    ::= { ringStationControlEntry 7 }

ringStationControlOrderChanges OBJECT-TYPE
    SYNTAX     Counter32
    MAX-ACCESS read-only
    STATUS     current
    DESCRIPTION
            "The number of add and delete events in the
            ringStationOrderTable optionally associated with
            this ringStationControlEntry."
    ::= { ringStationControlEntry 8 }

ringStationControlOwner OBJECT-TYPE
    SYNTAX     OwnerString
    MAX-ACCESS read-write
    STATUS     current
    DESCRIPTION
            "The entity that configured this entry and is
            therefore using the resources assigned to it."
    ::= { ringStationControlEntry 9 }

ringStationControlStatus OBJECT-TYPE
    SYNTAX     EntryStatus
    MAX-ACCESS read-write
    STATUS     current
    DESCRIPTION
            "The status of this ringStationControl entry.

            If this object is not equal to valid(1), all
            associated entries in the ringStationTable shall
            be deleted by the agent."
    ::= { ringStationControlEntry 10 }

ringStationTable OBJECT-TYPE
    SYNTAX     SEQUENCE OF RingStationEntry
    MAX-ACCESS not-accessible
    STATUS     current
    DESCRIPTION
            "A list of ring station entries.  An entry will
            exist for each station that is now or has
            previously been detected as physically present on
            this ring."
     ::= { tokenRing 2 }

ringStationEntry OBJECT-TYPE
    SYNTAX     RingStationEntry
    MAX-ACCESS not-accessible
    STATUS     current
    DESCRIPTION
            "A collection of statistics for a particular
            station that has been discovered on a ring
            monitored by this device."
    INDEX { ringStationIfIndex, ringStationMacAddress }
    ::= { ringStationTable 1 }

-- As an example, an instance of the ringStationStationStatus object
-- might be named ringStationStationStatus.1.16.0.90.0.64.131

RingStationEntry ::= SEQUENCE {
    ringStationIfIndex                InterfaceIndex,
    ringStationMacAddress             MacAddress,
    ringStationLastNAUN               MacAddress,
    ringStationStationStatus          INTEGER,
    ringStationLastEnterTime          TimeStamp,
    ringStationLastExitTime           TimeStamp,
    ringStationDuplicateAddresses     Counter32,
    ringStationInLineErrors           Counter32,
    ringStationOutLineErrors          Counter32,
    ringStationInternalErrors         Counter32,
    ringStationInBurstErrors          Counter32,
    ringStationOutBurstErrors         Counter32,
    ringStationACErrors               Counter32,
    ringStationAbortErrors            Counter32,
    ringStationLostFrameErrors        Counter32,
    ringStationCongestionErrors       Counter32,
    ringStationFrameCopiedErrors      Counter32,
    ringStationFrequencyErrors        Counter32,
    ringStationTokenErrors            Counter32,
    ringStationInBeaconErrors         Counter32,
    ringStationOutBeaconErrors        Counter32,
    ringStationInsertions             Counter32
}

ringStationIfIndex OBJECT-TYPE
    SYNTAX     InterfaceIndex
    MAX-ACCESS read-only
    STATUS     current
    DESCRIPTION
            "The value of this object uniquely identifies the
            interface on this remote network monitoring device
            on which this station was detected.  The interface
            identified by a particular value of this object is
            the same interface as identified by the same value
            of the ifIndex object, defined in IF-MIB [17]."
    ::= { ringStationEntry 1 }

ringStationMacAddress OBJECT-TYPE
    SYNTAX     MacAddress
    MAX-ACCESS read-only
    STATUS     current
    DESCRIPTION
            "The physical address of this station."
    ::= { ringStationEntry 2 }

ringStationLastNAUN OBJECT-TYPE
    SYNTAX     MacAddress
    MAX-ACCESS read-only
    STATUS     current
    DESCRIPTION
            "The physical address of last known NAUN of this
            station."
    ::= { ringStationEntry 3 }

ringStationStationStatus OBJECT-TYPE
    SYNTAX     INTEGER {
        active(1),          -- actively participating in ring poll.
        inactive(2),        -- Not participating in ring poll
        forcedRemoval(3)    -- Forced off ring by network management.
    }
    MAX-ACCESS read-only
    STATUS     current
    DESCRIPTION
            "The status of this station on the ring. A value
            of active(1) indicates the station is actively
            participating in ring poll. A value of inactive(2)
            indicates the station is not participating in ring
            poll and a value of forcedRemoval(3) indicates the
            station was forced off the ring by a network
            management operation."
    ::= { ringStationEntry 4 }

ringStationLastEnterTime OBJECT-TYPE
    SYNTAX     TimeStamp
    MAX-ACCESS read-only
    STATUS     current
    DESCRIPTION
            "The value of sysUpTime at the time this station
            last entered the ring.  If the time is unknown,
            this value shall be zero."
    ::= { ringStationEntry 5 }

ringStationLastExitTime OBJECT-TYPE
    SYNTAX     TimeStamp
    MAX-ACCESS read-only
    STATUS     current
    DESCRIPTION
            "The value of sysUpTime at the time the probe
            detected that this station last exited the ring.
            If the time is unknown, this value shall be zero."
    ::= { ringStationEntry 6 }

ringStationDuplicateAddresses OBJECT-TYPE
    SYNTAX     Counter32
    MAX-ACCESS read-only
    STATUS     current
    DESCRIPTION
            "The number of times this station experienced a
            duplicate address error."
    ::= { ringStationEntry 7 }

ringStationInLineErrors OBJECT-TYPE
    SYNTAX     Counter32
    MAX-ACCESS read-only
    STATUS     current
    DESCRIPTION
            "The total number of line errors reported by this
            station in error reporting packets detected by the
            probe."
    ::= { ringStationEntry 8 }

ringStationOutLineErrors OBJECT-TYPE
    SYNTAX     Counter32
    MAX-ACCESS read-only
    STATUS     current
    DESCRIPTION
            "The total number of line errors reported in error
            reporting packets sent by the nearest active
            downstream neighbor of this station and detected
            by the probe."
    ::= { ringStationEntry 9 }

ringStationInternalErrors OBJECT-TYPE
    SYNTAX     Counter32
    MAX-ACCESS read-only
    STATUS     current
    DESCRIPTION
            "The total number of adapter internal errors
            reported by this station in error reporting
            packets detected by the probe."
    ::= { ringStationEntry 10 }

ringStationInBurstErrors OBJECT-TYPE
    SYNTAX     Counter32
    MAX-ACCESS read-only
    STATUS     current
    DESCRIPTION
            "The total number of burst errors reported by this
            station in error reporting packets detected by the
            probe."
    ::= { ringStationEntry 11 }

ringStationOutBurstErrors OBJECT-TYPE
    SYNTAX     Counter32
    MAX-ACCESS read-only
    STATUS     current
    DESCRIPTION
            "The total number of burst errors reported in
            error reporting packets sent by the nearest active
            downstream neighbor of this station and detected
            by the probe."
    ::= { ringStationEntry 12 }

ringStationACErrors OBJECT-TYPE
    SYNTAX     Counter32
    MAX-ACCESS read-only
    STATUS     current
    DESCRIPTION
            "The total number of AC (Address Copied) errors
            reported in error reporting packets sent by the
            nearest active downstream neighbor of this station
            and detected by the probe."
    ::= { ringStationEntry 13 }

ringStationAbortErrors OBJECT-TYPE
    SYNTAX     Counter32
    MAX-ACCESS read-only
    STATUS     current
    DESCRIPTION
            "The total number of abort delimiters reported by
            this station in error reporting packets detected
            by the probe."
    ::= { ringStationEntry 14 }

ringStationLostFrameErrors OBJECT-TYPE
    SYNTAX     Counter32
    MAX-ACCESS read-only
    STATUS     current
    DESCRIPTION
            "The total number of lost frame errors reported by
            this station in error reporting packets detected
            by the probe."
    ::= { ringStationEntry 15 }

ringStationCongestionErrors OBJECT-TYPE
    SYNTAX     Counter32
    MAX-ACCESS read-only
    STATUS     current
    DESCRIPTION
            "The total number of receive congestion errors
            reported by this station in error reporting
            packets detected by the probe."
    ::= { ringStationEntry 16 }

ringStationFrameCopiedErrors OBJECT-TYPE
    SYNTAX     Counter32
    MAX-ACCESS read-only
    STATUS     current
    DESCRIPTION
            "The total number of frame copied errors reported
            by this station in error reporting packets
            detected by the probe."
    ::= { ringStationEntry 17 }

ringStationFrequencyErrors OBJECT-TYPE
    SYNTAX     Counter32
    MAX-ACCESS read-only
    STATUS     current
    DESCRIPTION
            "The total number of frequency errors reported by
            this station in error reporting packets detected
            by the probe."
    ::= { ringStationEntry 18 }

ringStationTokenErrors OBJECT-TYPE
    SYNTAX     Counter32
    MAX-ACCESS read-only
    STATUS     current
    DESCRIPTION
            "The total number of token errors reported by this
            station in error reporting frames detected by the
            probe."
    ::= { ringStationEntry 19 }

ringStationInBeaconErrors OBJECT-TYPE
    SYNTAX     Counter32
    MAX-ACCESS read-only
    STATUS     current
    DESCRIPTION
            "The total number of beacon frames sent by this
            station and detected by the probe."
    ::= { ringStationEntry 20 }

ringStationOutBeaconErrors OBJECT-TYPE
    SYNTAX     Counter32
    MAX-ACCESS read-only
    STATUS     current
    DESCRIPTION
            "The total number of beacon frames detected by the
            probe that name this station as the NAUN."
    ::= { ringStationEntry 21 }

ringStationInsertions OBJECT-TYPE
    SYNTAX     Counter32
    MAX-ACCESS read-only
    STATUS     current
    DESCRIPTION
            "The number of times the probe detected this
            station inserting onto the ring."
    ::= { ringStationEntry 22 }

-- The Token Ring Ring Station Order Group
--
-- Implementation of this group is optional
-- Consult the MODULE-COMPLIANCE macro for the authoritative
-- conformance information for this MIB.
--

-- The ringStationOrderTable

ringStationOrderTable OBJECT-TYPE
    SYNTAX     SEQUENCE OF RingStationOrderEntry
    MAX-ACCESS not-accessible
    STATUS     current
    DESCRIPTION
            "A list of ring station entries for stations in
            the ring poll, ordered by their ring-order."
    ::= { tokenRing 3 }

ringStationOrderEntry OBJECT-TYPE
    SYNTAX     RingStationOrderEntry
    MAX-ACCESS not-accessible
    STATUS     current
    DESCRIPTION
            "A collection of statistics for a particular
            station that is active on a ring monitored by this
            device.  If implemented, this table will contain
            information for every interface that has a
            ringStationControlStatus equal to valid."
    INDEX { ringStationOrderIfIndex, ringStationOrderOrderIndex }
    ::= { ringStationOrderTable 1 }

-- As an example, an instance of the ringStationOrderMacAddress
-- object might be named ringStationOrderMacAddress.1.14

RingStationOrderEntry ::= SEQUENCE {
    ringStationOrderIfIndex             InterfaceIndex,
    ringStationOrderOrderIndex          Integer32,
    ringStationOrderMacAddress          MacAddress
}

ringStationOrderIfIndex OBJECT-TYPE
    SYNTAX     InterfaceIndex
    MAX-ACCESS read-only
    STATUS     current
    DESCRIPTION
            "The value of this object uniquely identifies the
            interface on this remote network monitoring device
            on which this station was detected.  The interface
            identified by a particular value of this object is
            the same interface as identified by the same value
            of the ifIndex object, defined in IF-MIB [17]."
    ::= { ringStationOrderEntry 1 }

ringStationOrderOrderIndex OBJECT-TYPE
    SYNTAX     Integer32 (1..2147483647)
    MAX-ACCESS read-only
    STATUS     current
    DESCRIPTION
            "This index denotes the location of this station
            with respect to other stations on the ring.  This
            index is one more than the number of hops
            downstream that this station is from the rmon
            probe.  The rmon probe itself gets the value one."
    ::= { ringStationOrderEntry 2 }

ringStationOrderMacAddress OBJECT-TYPE
    SYNTAX     MacAddress
    MAX-ACCESS read-only
    STATUS     current
    DESCRIPTION
            "The physical address of this station."
    ::= { ringStationOrderEntry 3 }

-- The Token Ring Ring Station Config Group
--
-- Implementation of this group is optional.
-- Consult the MODULE-COMPLIANCE macro for the authoritative
-- conformance information for this MIB.
--
-- The ring station config group manages token ring nodes through
-- active means.

ringStationConfigControlTable OBJECT-TYPE
    SYNTAX     SEQUENCE OF RingStationConfigControlEntry
    MAX-ACCESS not-accessible
    STATUS     current
    DESCRIPTION
            "A list of ring station configuration control
            entries."
    ::= { tokenRing 4 }

ringStationConfigControlEntry OBJECT-TYPE
    SYNTAX     RingStationConfigControlEntry
    MAX-ACCESS not-accessible
    STATUS     current
    DESCRIPTION
            "This entry controls active management of stations
            by the probe.  One entry exists in this table for
            each active station in the ringStationTable."
    INDEX { ringStationConfigControlIfIndex,
            ringStationConfigControlMacAddress }
    ::= { ringStationConfigControlTable 1 }

-- As an example, an instance of the ringStationConfigControlRemove
-- object might be named
-- ringStationConfigControlRemove.1.16.0.90.0.64.131

RingStationConfigControlEntry ::= SEQUENCE {
    ringStationConfigControlIfIndex         InterfaceIndex,
    ringStationConfigControlMacAddress      MacAddress,
    ringStationConfigControlRemove          INTEGER,
    ringStationConfigControlUpdateStats     INTEGER
}

ringStationConfigControlIfIndex OBJECT-TYPE
    SYNTAX     InterfaceIndex
    MAX-ACCESS read-only
    STATUS     current
    DESCRIPTION
            "The value of this object uniquely identifies the
            interface on this remote network monitoring device
            on which this station was detected.  The interface
            identified by a particular value of this object is
            the same interface as identified by the same value
            of the ifIndex object, defined in IF-MIB [17]."
    ::= { ringStationConfigControlEntry 1 }

ringStationConfigControlMacAddress OBJECT-TYPE
    SYNTAX     MacAddress
    MAX-ACCESS read-only
    STATUS     current
    DESCRIPTION
            "The physical address of this station."
    ::= { ringStationConfigControlEntry 2 }

ringStationConfigControlRemove OBJECT-TYPE
    SYNTAX     INTEGER {
        stable(1),
        removing(2)
    }
    MAX-ACCESS read-write
    STATUS     current
    DESCRIPTION
            "Setting this object to `removing(2)' causes a
            Remove Station MAC frame to be sent.  The agent
            will set this object to `stable(1)' after
            processing the request."
    ::= { ringStationConfigControlEntry 3 }

ringStationConfigControlUpdateStats OBJECT-TYPE
    SYNTAX     INTEGER {
        stable(1),
        updating(2)
    }
    MAX-ACCESS read-write
    STATUS     current
    DESCRIPTION
            "Setting this object to `updating(2)' causes the
            configuration information associate with this
            entry to be updated.  The agent will set this
            object to `stable(1)' after processing the
            request."
    ::= { ringStationConfigControlEntry 4 }

--  The ringStationConfig Table
--
--  Entries exist in this table after an active
--  configuration query has completed successfully for
--  a station.  This query is initiated by the associated
--  ringStationConfigControlUpdateStats variable.


ringStationConfigTable OBJECT-TYPE
    SYNTAX     SEQUENCE OF RingStationConfigEntry
    MAX-ACCESS not-accessible
    STATUS     current
    DESCRIPTION
            "A list of configuration entries for stations on a
            ring monitored by this probe."
    ::= { tokenRing 5 }

ringStationConfigEntry OBJECT-TYPE
    SYNTAX     RingStationConfigEntry
    MAX-ACCESS not-accessible
    STATUS     current
    DESCRIPTION
            "A collection of statistics for a particular
            station that has been discovered on a ring
            monitored by this probe."
    INDEX { ringStationConfigIfIndex, ringStationConfigMacAddress }
    ::= { ringStationConfigTable 1 }

-- As an example, an instance of the ringStationConfigLocation object
-- might be named ringStationConfigLocation.1.16.0.90.0.64.131

RingStationConfigEntry ::= SEQUENCE {
    ringStationConfigIfIndex            InterfaceIndex,
    ringStationConfigMacAddress         MacAddress,
    ringStationConfigUpdateTime         TimeStamp,
    ringStationConfigLocation           OCTET STRING,
    ringStationConfigMicrocode          OCTET STRING,
    ringStationConfigGroupAddress       OCTET STRING,
    ringStationConfigFunctionalAddress  OCTET STRING
}

ringStationConfigIfIndex OBJECT-TYPE
    SYNTAX     InterfaceIndex
    MAX-ACCESS read-only
    STATUS     current
    DESCRIPTION
            "The value of this object uniquely identifies the
            interface on this remote network monitoring device
            on which this station was detected.  The interface
            identified by a particular value of this object is
            the same interface as identified by the same value
            of the ifIndex object, defined in IF-MIB [17]."
    ::= { ringStationConfigEntry 1 }

ringStationConfigMacAddress OBJECT-TYPE
    SYNTAX     MacAddress
    MAX-ACCESS read-only
    STATUS     current
    DESCRIPTION
            "The physical address of this station."
    ::= { ringStationConfigEntry 2 }

ringStationConfigUpdateTime OBJECT-TYPE
    SYNTAX     TimeStamp
    MAX-ACCESS read-only
    STATUS     current
    DESCRIPTION
            "The value of sysUpTime at the time this
            configuration information was last updated
            (completely)."
    ::= { ringStationConfigEntry 3 }

ringStationConfigLocation OBJECT-TYPE
    SYNTAX     OCTET STRING (SIZE(4))
    MAX-ACCESS read-only
    STATUS     current
    DESCRIPTION
            "The assigned physical location of this station."
    ::= { ringStationConfigEntry 4 }

ringStationConfigMicrocode OBJECT-TYPE
    SYNTAX     OCTET STRING (SIZE(10))
    MAX-ACCESS read-only
    STATUS     current
    DESCRIPTION
            "The microcode EC level of this station."
    ::= { ringStationConfigEntry 5 }

ringStationConfigGroupAddress OBJECT-TYPE
    SYNTAX     OCTET STRING (SIZE(4))
    MAX-ACCESS read-only
    STATUS     current
    DESCRIPTION
            "The low-order 4 octets of the group address
            recognized by this station."
    ::= { ringStationConfigEntry 6 }

ringStationConfigFunctionalAddress OBJECT-TYPE
    SYNTAX     OCTET STRING (SIZE(4))
    MAX-ACCESS read-only
    STATUS     current
    DESCRIPTION
            "the functional addresses recognized by this
            station."
    ::= { ringStationConfigEntry 7 }

-- The Token Ring Source Routing group
--
-- Implementation of this group is optional.
-- Consult the MODULE-COMPLIANCE macro for the authoritative
-- conformance information for this MIB.
--
-- The data in this group is collected from the source routing
-- information potentially present in any token ring packet.
-- This information will be valid only in a pure source route
-- bridging environment.  In a transparent bridging or a mixed
-- bridging environment, this information may not be accurate.

sourceRoutingStatsTable OBJECT-TYPE
    SYNTAX     SEQUENCE OF SourceRoutingStatsEntry
    MAX-ACCESS not-accessible
    STATUS     current
    DESCRIPTION
            "A list of source routing statistics entries."
    ::= { tokenRing 6 }

sourceRoutingStatsEntry OBJECT-TYPE
    SYNTAX     SourceRoutingStatsEntry
    MAX-ACCESS not-accessible
    STATUS     current
    DESCRIPTION
            "A collection of source routing statistics kept
            for a particular Token Ring interface."
    INDEX { sourceRoutingStatsIfIndex }
    ::= { sourceRoutingStatsTable 1 }

-- As an example, an instance of the sourceRoutingStatsInFrames
-- object might be named sourceRoutingStatsInFrames.1

SourceRoutingStatsEntry ::= SEQUENCE {
    sourceRoutingStatsIfIndex                      InterfaceIndex,
    sourceRoutingStatsRingNumber                   Integer32,
    sourceRoutingStatsInFrames                     Counter32,
        -- in to our net

    sourceRoutingStatsOutFrames                    Counter32,
        -- out from our net

    sourceRoutingStatsThroughFrames                Counter32,
        -- through our net

    sourceRoutingStatsAllRoutesBroadcastFrames     Counter32,
    sourceRoutingStatsSingleRouteBroadcastFrames   Counter32,
    sourceRoutingStatsInOctets                     Counter32,
    sourceRoutingStatsOutOctets                    Counter32,
    sourceRoutingStatsThroughOctets                Counter32,
    sourceRoutingStatsAllRoutesBroadcastOctets     Counter32,
    sourceRoutingStatsSingleRoutesBroadcastOctets  Counter32,
    sourceRoutingStatsLocalLLCFrames               Counter32,
    sourceRoutingStats1HopFrames                   Counter32,
    sourceRoutingStats2HopsFrames                  Counter32,
    sourceRoutingStats3HopsFrames                  Counter32,
    sourceRoutingStats4HopsFrames                  Counter32,
    sourceRoutingStats5HopsFrames                  Counter32,
    sourceRoutingStats6HopsFrames                  Counter32,
    sourceRoutingStats7HopsFrames                  Counter32,
    sourceRoutingStats8HopsFrames                  Counter32,
    sourceRoutingStatsMoreThan8HopsFrames          Counter32,
    sourceRoutingStatsOwner                        OwnerString,
    sourceRoutingStatsStatus                       EntryStatus
}

sourceRoutingStatsIfIndex OBJECT-TYPE
    SYNTAX     InterfaceIndex
    MAX-ACCESS read-only
    STATUS     current
    DESCRIPTION
            "The value of this object uniquely identifies the
            interface on this remote network monitoring device
            on which source routing statistics will be
            detected.  The interface identified by a
            particular value of this object is the same
            interface as identified by the same value of the
            ifIndex object, defined in IF-MIB [17]."
    ::= { sourceRoutingStatsEntry 1 }

sourceRoutingStatsRingNumber OBJECT-TYPE
    SYNTAX     Integer32
    MAX-ACCESS read-only
    STATUS     current
    DESCRIPTION
            "The ring number of the ring monitored by this
            entry.  When any object in this entry is created,
            the probe will attempt to discover the ring
            number.  Only after the ring number is discovered
            will this object be created.  After creating an
            object in this entry, the management station
            should poll this object to detect when it is
            created.  Only after this object is created can
            the management station set the
            sourceRoutingStatsStatus entry to valid(1)."
    ::= { sourceRoutingStatsEntry 2 }

sourceRoutingStatsInFrames OBJECT-TYPE
    SYNTAX     Counter32
    MAX-ACCESS read-only
    STATUS     current
    DESCRIPTION
            "The count of frames sent into this ring from
            another ring that were not All Routes Broadcasts
            or Single Route Broadcast."
    ::= { sourceRoutingStatsEntry 3 }

sourceRoutingStatsOutFrames OBJECT-TYPE
    SYNTAX     Counter32
    MAX-ACCESS read-only
    STATUS     current
    DESCRIPTION
            "The count of frames sent from this ring to
            another ring that were not All Routes Broadcasts
            or Single Route Broadcast."
    ::= { sourceRoutingStatsEntry 4 }

sourceRoutingStatsThroughFrames OBJECT-TYPE
    SYNTAX     Counter32
    MAX-ACCESS read-only
    STATUS     current
    DESCRIPTION
            "The count of frames sent from another ring,
            through this ring, to another ring that were not
            All Routes Broadcasts or Single Route Broadcast."
    ::= { sourceRoutingStatsEntry 5 }

sourceRoutingStatsAllRoutesBroadcastFrames OBJECT-TYPE
    SYNTAX     Counter32
    MAX-ACCESS read-only
    STATUS     current
    DESCRIPTION
            "The total number of good frames received that
            were All Routes Broadcast."
    ::= { sourceRoutingStatsEntry 6 }

sourceRoutingStatsSingleRouteBroadcastFrames OBJECT-TYPE
    SYNTAX     Counter32
    MAX-ACCESS read-only
    STATUS     current
    DESCRIPTION
            "The total number of good frames received that
            were Single Route Broadcast."
    ::= { sourceRoutingStatsEntry 7 }

sourceRoutingStatsInOctets OBJECT-TYPE
    SYNTAX     Counter32
    MAX-ACCESS read-only
    STATUS     current
    DESCRIPTION
            "The count of octets in good frames sent into this
            ring from another ring that were not All Routes
            Broadcasts or Single Route Broadcast."
    ::= { sourceRoutingStatsEntry 8 }

sourceRoutingStatsOutOctets OBJECT-TYPE
    SYNTAX     Counter32
    MAX-ACCESS read-only
    STATUS     current
    DESCRIPTION
            "The count of octets in good frames sent from this
            ring to another ring that were not All Routes
            Broadcasts or Single Route Broadcast."
    ::= { sourceRoutingStatsEntry 9 }

sourceRoutingStatsThroughOctets OBJECT-TYPE
    SYNTAX     Counter32
    MAX-ACCESS read-only
    STATUS     current
    DESCRIPTION
            "The count of octets in good frames sent another
            ring, through this ring, to another ring that were
            not All Routes Broadcasts or Single Route
            Broadcast."
    ::= { sourceRoutingStatsEntry 10 }

sourceRoutingStatsAllRoutesBroadcastOctets OBJECT-TYPE
    SYNTAX     Counter32
    MAX-ACCESS read-only
    STATUS     current
    DESCRIPTION
            "The total number of octets in good frames
            received that were All Routes Broadcast."
    ::= { sourceRoutingStatsEntry 11 }

sourceRoutingStatsSingleRoutesBroadcastOctets OBJECT-TYPE
    SYNTAX     Counter32
    MAX-ACCESS read-only
    STATUS     current
    DESCRIPTION
            "The total number of octets in good frames
            received that were Single Route Broadcast."
    ::= { sourceRoutingStatsEntry 12 }

sourceRoutingStatsLocalLLCFrames OBJECT-TYPE
    SYNTAX     Counter32
    MAX-ACCESS read-only
    STATUS     current
    DESCRIPTION
            "The total number of frames received which had no
            RIF field (or had a RIF field that only included
            the local ring's number) and were not All Route
            Broadcast Frames or Single Route Broadcast
            Frames."
    ::= { sourceRoutingStatsEntry 13 }

sourceRoutingStats1HopFrames OBJECT-TYPE
    SYNTAX     Counter32
    MAX-ACCESS read-only
    STATUS     current
    DESCRIPTION
            "The total number of frames received whose route
            had 1 hop, were not All Route Broadcast Frames or
            Single Route Broadcast Frames, and whose source or
            destination were on this ring (i.e. frames that
            had a RIF field and had this ring number in the
            first or last entry of the RIF field)."
    ::= { sourceRoutingStatsEntry 14 }

sourceRoutingStats2HopsFrames OBJECT-TYPE
    SYNTAX     Counter32
    MAX-ACCESS read-only
    STATUS     current
    DESCRIPTION
            "The total number of frames received whose route
            had 2 hops, were not All Route Broadcast Frames or
            Single Route Broadcast Frames, and whose source or
            destination were on this ring (i.e. frames that
            had a RIF field and had this ring number in the
            first or last entry of the RIF field)."
    ::= { sourceRoutingStatsEntry 15 }

sourceRoutingStats3HopsFrames OBJECT-TYPE
    SYNTAX     Counter32
    MAX-ACCESS read-only
    STATUS     current
    DESCRIPTION
            "The total number of frames received whose route
            had 3 hops, were not All Route Broadcast Frames or
            Single Route Broadcast Frames, and whose source or
            destination were on this ring (i.e. frames that
            had a RIF field and had this ring number in the
            first or last entry of the RIF field)."
    ::= { sourceRoutingStatsEntry 16 }

sourceRoutingStats4HopsFrames OBJECT-TYPE
    SYNTAX     Counter32
    MAX-ACCESS read-only
    STATUS     current
    DESCRIPTION
            "The total number of frames received whose route
            had 4 hops, were not All Route Broadcast Frames or
            Single Route Broadcast Frames, and whose source or
            destination were on this ring (i.e. frames that
            had a RIF field and had this ring number in the
            first or last entry of the RIF field)."
    ::= { sourceRoutingStatsEntry 17 }

sourceRoutingStats5HopsFrames OBJECT-TYPE
    SYNTAX     Counter32
    MAX-ACCESS read-only
    STATUS     current
    DESCRIPTION
            "The total number of frames received whose route
            had 5 hops, were not All Route Broadcast Frames or
            Single Route Broadcast Frames, and whose source or
            destination were on this ring (i.e. frames that
            had a RIF field and had this ring number in the
            first or last entry of the RIF field)."
    ::= { sourceRoutingStatsEntry 18 }

sourceRoutingStats6HopsFrames OBJECT-TYPE
    SYNTAX     Counter32
    MAX-ACCESS read-only
    STATUS     current
    DESCRIPTION
            "The total number of frames received whose route
            had 6 hops, were not All Route Broadcast Frames or
            Single Route Broadcast Frames, and whose source or
            destination were on this ring (i.e. frames that
            had a RIF field and had this ring number in the
            first or last entry of the RIF field)."
    ::= { sourceRoutingStatsEntry 19 }

sourceRoutingStats7HopsFrames OBJECT-TYPE
    SYNTAX     Counter32
    MAX-ACCESS read-only
    STATUS     current
    DESCRIPTION
            "The total number of frames received whose route
            had 7 hops, were not All Route Broadcast Frames or
            Single Route Broadcast Frames, and whose source or
            destination were on this ring (i.e. frames that
            had a RIF field and had this ring number in the
            first or last entry of the RIF field)."
    ::= { sourceRoutingStatsEntry 20 }

sourceRoutingStats8HopsFrames OBJECT-TYPE
    SYNTAX     Counter32
    MAX-ACCESS read-only
    STATUS     current
    DESCRIPTION
            "The total number of frames received whose route
            had 8 hops, were not All Route Broadcast Frames or
            Single Route Broadcast Frames, and whose source or
            destination were on this ring (i.e. frames that
            had a RIF field and had this ring number in the
            first or last entry of the RIF field)."
    ::= { sourceRoutingStatsEntry 21 }

sourceRoutingStatsMoreThan8HopsFrames OBJECT-TYPE
    SYNTAX     Counter32
    MAX-ACCESS read-only
    STATUS     current
    DESCRIPTION
            "The total number of frames received whose route
            had more than 8 hops, were not All Route Broadcast
            Frames or Single Route Broadcast Frames, and whose
            source or destination were on this ring (i.e.
            frames that had a RIF field and had this ring
            number in the first or last entry of the RIF
            field)."
    ::= { sourceRoutingStatsEntry 22 }

sourceRoutingStatsOwner OBJECT-TYPE
    SYNTAX     OwnerString
    MAX-ACCESS read-write
    STATUS     current
    DESCRIPTION
            "The entity that configured this entry and is
            therefore using the resources assigned to it."
    ::= { sourceRoutingStatsEntry 23 }

sourceRoutingStatsStatus OBJECT-TYPE
    SYNTAX     EntryStatus
    MAX-ACCESS read-write
    STATUS     current
    DESCRIPTION
            "The status of this sourceRoutingStats entry."
    ::= { sourceRoutingStatsEntry 24 }

-- Compliance Statements
tokenRingRMONCompliance MODULE-COMPLIANCE
    STATUS current
    DESCRIPTION
        "At least one of the groups in this module must be
        implemented to conform to the Token Ring RMON MIB.
        Implementations of this MIB must also implement the
        system group of MIB-II [16] and the IF-MIB [17]."
    MODULE -- this module

      GROUP tokenRingMLStatsGroup
          DESCRIPTION
              "The Token Ring Mac-Layer Statistics Group is optional."

      GROUP tokenRingPStatsGroup
          DESCRIPTION
              "The Token Ring Promiscuous Statistics Group is optional."

      GROUP tokenRingMLHistoryGroup
          DESCRIPTION
              "The Token Ring Mac-Layer History Group is optional.
              Implementation of this group requires implementation of
              the historyControl group from RFC2819."

      GROUP tokenRingPHistoryGroup
          DESCRIPTION
              "The Token Ring Promiscuous History Group is optional.
              Implementation of this group requires implementation of
              the historyControl group from RFC2819."

      GROUP ringStationGroup
          DESCRIPTION
              "The Token Ring Ring Station Group is optional."

      GROUP ringStationOrderGroup
          DESCRIPTION
              "The Token Ring Ring Station Order Group is optional."

      GROUP ringStationConfigGroup
          DESCRIPTION
              "The Token Ring Ring Station Config Group is optional."

      GROUP sourceRoutingStatsGroup
          DESCRIPTION
              "The Token Ring Source Routing Group is optional."

    ::= { rmonCompliances 2 }

    tokenRingMLStatsGroup OBJECT-GROUP
        OBJECTS {
            tokenRingMLStatsIndex, tokenRingMLStatsDataSource,
            tokenRingMLStatsDropEvents, tokenRingMLStatsMacOctets,
            tokenRingMLStatsMacPkts, tokenRingMLStatsRingPurgeEvents,
            tokenRingMLStatsRingPurgePkts,
            tokenRingMLStatsBeaconEvents, tokenRingMLStatsBeaconTime,
            tokenRingMLStatsBeaconPkts,
            tokenRingMLStatsClaimTokenEvents,
            tokenRingMLStatsClaimTokenPkts,
            tokenRingMLStatsNAUNChanges, tokenRingMLStatsLineErrors,
            tokenRingMLStatsInternalErrors,
            tokenRingMLStatsBurstErrors, tokenRingMLStatsACErrors,
            tokenRingMLStatsAbortErrors,
            tokenRingMLStatsLostFrameErrors,
            tokenRingMLStatsCongestionErrors,
            tokenRingMLStatsFrameCopiedErrors,
            tokenRingMLStatsFrequencyErrors,
            tokenRingMLStatsTokenErrors,
            tokenRingMLStatsSoftErrorReports,
            tokenRingMLStatsRingPollEvents,
            tokenRingMLStatsOwner, tokenRingMLStatsStatus
        }
        STATUS current
        DESCRIPTION
            "The Token Ring Mac-Layer Statistics Group."
        ::= { rmonGroups 12 }

    tokenRingPStatsGroup OBJECT-GROUP
        OBJECTS {
            tokenRingPStatsIndex, tokenRingPStatsDataSource,
            tokenRingPStatsDropEvents, tokenRingPStatsDataOctets,
            tokenRingPStatsDataPkts, tokenRingPStatsDataBroadcastPkts,
            tokenRingPStatsDataMulticastPkts,
            tokenRingPStatsDataPkts18to63Octets,
            tokenRingPStatsDataPkts64to127Octets,
            tokenRingPStatsDataPkts128to255Octets,
            tokenRingPStatsDataPkts256to511Octets,
            tokenRingPStatsDataPkts512to1023Octets,
            tokenRingPStatsDataPkts1024to2047Octets,
            tokenRingPStatsDataPkts2048to4095Octets,
            tokenRingPStatsDataPkts4096to8191Octets,
            tokenRingPStatsDataPkts8192to18000Octets,
            tokenRingPStatsDataPktsGreaterThan18000Octets,
            tokenRingPStatsOwner, tokenRingPStatsStatus
        }
        STATUS current
        DESCRIPTION
            "The Token Ring Promiscuous Statistics Group."
        ::= { rmonGroups 13 }

    tokenRingMLHistoryGroup OBJECT-GROUP
        OBJECTS {
            tokenRingMLHistoryIndex, tokenRingMLHistorySampleIndex,
            tokenRingMLHistoryIntervalStart,
            tokenRingMLHistoryDropEvents,
            tokenRingMLHistoryMacOctets,
            tokenRingMLHistoryMacPkts,
            tokenRingMLHistoryRingPurgeEvents,
            tokenRingMLHistoryRingPurgePkts,
            tokenRingMLHistoryBeaconEvents,
            tokenRingMLHistoryBeaconTime,
            tokenRingMLHistoryBeaconPkts,
            tokenRingMLHistoryClaimTokenEvents,
            tokenRingMLHistoryClaimTokenPkts,
            tokenRingMLHistoryNAUNChanges,
            tokenRingMLHistoryLineErrors,
            tokenRingMLHistoryInternalErrors,
            tokenRingMLHistoryBurstErrors,
            tokenRingMLHistoryACErrors,
            tokenRingMLHistoryAbortErrors,
            tokenRingMLHistoryLostFrameErrors,
            tokenRingMLHistoryCongestionErrors,
            tokenRingMLHistoryFrameCopiedErrors,
            tokenRingMLHistoryFrequencyErrors,
            tokenRingMLHistoryTokenErrors,
            tokenRingMLHistorySoftErrorReports,
            tokenRingMLHistoryRingPollEvents,
            tokenRingMLHistoryActiveStations
        }
        STATUS current
        DESCRIPTION
            "The Token Ring Mac-Layer History Group."
        ::= { rmonGroups 14 }

    tokenRingPHistoryGroup OBJECT-GROUP
        OBJECTS {
            tokenRingPHistoryIndex, tokenRingPHistorySampleIndex,
            tokenRingPHistoryIntervalStart,
            tokenRingPHistoryDropEvents,
            tokenRingPHistoryDataOctets,
            tokenRingPHistoryDataPkts,
            tokenRingPHistoryDataBroadcastPkts,
            tokenRingPHistoryDataMulticastPkts,
            tokenRingPHistoryDataPkts18to63Octets,
            tokenRingPHistoryDataPkts64to127Octets,
            tokenRingPHistoryDataPkts128to255Octets,
            tokenRingPHistoryDataPkts256to511Octets,
            tokenRingPHistoryDataPkts512to1023Octets,
            tokenRingPHistoryDataPkts1024to2047Octets,
            tokenRingPHistoryDataPkts2048to4095Octets,
            tokenRingPHistoryDataPkts4096to8191Octets,
            tokenRingPHistoryDataPkts8192to18000Octets,
            tokenRingPHistoryDataPktsGreaterThan18000Octets
        }
        STATUS current
        DESCRIPTION
            "The Token Ring Promiscuous History Group."
        ::= { rmonGroups 15 }

    ringStationGroup OBJECT-GROUP
        OBJECTS {
            ringStationControlIfIndex,
            ringStationControlTableSize,
            ringStationControlActiveStations,
            ringStationControlRingState,
            ringStationControlBeaconSender,
            ringStationControlBeaconNAUN,
            ringStationControlActiveMonitor,
            ringStationControlOrderChanges,
            ringStationControlOwner, ringStationControlStatus,
            ringStationIfIndex, ringStationMacAddress,
            ringStationLastNAUN, ringStationStationStatus,
            ringStationLastEnterTime, ringStationLastExitTime,
            ringStationDuplicateAddresses, ringStationInLineErrors,
            ringStationOutLineErrors, ringStationInternalErrors,
            ringStationInBurstErrors, ringStationOutBurstErrors,
            ringStationACErrors, ringStationAbortErrors,
            ringStationLostFrameErrors, ringStationCongestionErrors,
            ringStationFrameCopiedErrors, ringStationFrequencyErrors,
            ringStationTokenErrors, ringStationInBeaconErrors,
            ringStationOutBeaconErrors, ringStationInsertions
        }
        STATUS current
        DESCRIPTION
            "The Token Ring Ring Station Group."
        ::= { rmonGroups 16 }

    ringStationOrderGroup OBJECT-GROUP
        OBJECTS {
            ringStationOrderIfIndex, ringStationOrderOrderIndex,
            ringStationOrderMacAddress
        }
        STATUS current
        DESCRIPTION
            "The Token Ring Ring Station Order Group."
        ::= { rmonGroups 17 }

    ringStationConfigGroup OBJECT-GROUP
        OBJECTS {
            ringStationConfigControlIfIndex,
            ringStationConfigControlMacAddress,
            ringStationConfigControlRemove,
            ringStationConfigControlUpdateStats,
            ringStationConfigIfIndex, ringStationConfigMacAddress,
            ringStationConfigUpdateTime, ringStationConfigLocation,
            ringStationConfigMicrocode, ringStationConfigGroupAddress,
            ringStationConfigFunctionalAddress
        }
        STATUS current
        DESCRIPTION
            "The Token Ring Ring Station Config Group."
        ::= { rmonGroups 18 }

    sourceRoutingStatsGroup OBJECT-GROUP
        OBJECTS {
            sourceRoutingStatsIfIndex, sourceRoutingStatsRingNumber,
            sourceRoutingStatsInFrames, sourceRoutingStatsOutFrames,
            sourceRoutingStatsThroughFrames,
            sourceRoutingStatsAllRoutesBroadcastFrames,
            sourceRoutingStatsSingleRouteBroadcastFrames,
            sourceRoutingStatsInOctets,
            sourceRoutingStatsOutOctets,
            sourceRoutingStatsThroughOctets,
            sourceRoutingStatsAllRoutesBroadcastOctets,
            sourceRoutingStatsSingleRoutesBroadcastOctets,
            sourceRoutingStatsLocalLLCFrames,
            sourceRoutingStats1HopFrames,
            sourceRoutingStats2HopsFrames,
            sourceRoutingStats3HopsFrames,
            sourceRoutingStats4HopsFrames,
            sourceRoutingStats5HopsFrames,
            sourceRoutingStats6HopsFrames,
            sourceRoutingStats7HopsFrames,
            sourceRoutingStats8HopsFrames,
            sourceRoutingStatsMoreThan8HopsFrames,
            sourceRoutingStatsOwner, sourceRoutingStatsStatus
        }
        STATUS current
        DESCRIPTION
            "The Token Ring Source Routing Group."
        ::= { rmonGroups 19 }

END
