EVAPA-MIB DEFINITIONS ::= BEGIN

-- This MIB built using parse file: HSV300_event_CD1231_09006000.txt 081104

-- ****************************************************************************
--
--         StorageWorks cpqHSV Management Information Base (MIB)
--         Management Information Base for SNMP Network Management
--
--
--      Copyright 1999, Compaq Computer Corporation.
--      Copyright 2010, Hewlett-Packard Company.
--      All Rights Reserved.
--
--      The information in this document is subject to change without notice.
--
--      COMPAQ COMPUTER CORPORATION SHALL NOT BE LIABLE FOR TECHNICAL
--      OR EDITORIAL ERRORS OR OMISSIONS CONTAINED HEREIN; NOR FOR INCIDENTAL
--      OR CONSEQUENTIAL DAMAGES RESULTING FROM THE FURNISHING, PERFORMANCE,
--      OR USE OF THIS MATERIAL.
--
--      The HP StorageWorks maHSV1x0 MIB provides HSV Controller information,
--      and HSV Management Agent information.
--
--      The Compaq Enterprise number is 232.
--      The ASN.1 prefix to, and including the Compaq Enterprise is:
--           1.3.6.1.4.1.232
--      iso(1) org(3) dod(6) internet(1) private(4) enterprises(1) compaq(232)
-- ****************************************************************************



	 IMPORTS
		 enterprises             FROM RFC1155-SMI
		 OBJECT-TYPE		 FROM RFC-1212
		 DisplayString           FROM RFC1213-MIB
		 IpAddress               FROM RFC1155-SMI 
                 TRAP-TYPE               FROM RFC-1215;
                 

	hp             OBJECT IDENTIFIER ::= { enterprises 232 } 
	hpevapa        OBJECT IDENTIFIER ::= { hp 175 }
        hpevent             OBJECT IDENTIFIER ::= { hpevapa 1 }


 
  hpevapaTraps OBJECT IDENTIFIER
    ::= { hpevent 1 }  

-- ********************************************************************	
	
	hpevapaServer OBJECT-TYPE
	    SYNTAX      DisplayString
	    ACCESS      read-only
	    STATUS      mandatory
	    DESCRIPTION 
	        "EVAPA Server which generates the event."
    ::= { hpevapaTraps 1 }
    

        hpevapaSequence_Number OBJECT-TYPE
            SYNTAX      OCTET STRING
            ACCESS      read-only
            STATUS      mandatory
            DESCRIPTION 
                "EVAPA Server Sequence identifier"
    ::= { hpevapaTraps 2 }
    
    	hpevapaEvent_Code OBJECT-TYPE
    	    SYNTAX  INTEGER
    	    ACCESS  read-only
    	    STATUS  mandatory
    	    DESCRIPTION
    		     "The management agent event code."
    ::= { hpevapaTraps 3 }

        hpevapaCategory OBJECT-TYPE
            SYNTAX      OCTET STRING
            ACCESS      read-only
            STATUS      mandatory
            DESCRIPTION 
                     "Source of the event"
    ::= { hpevapaTraps 4 }
    
        hpevapaTime_Detect OBJECT-TYPE
	    SYNTAX  DisplayString
	    ACCESS  read-only
	    STATUS  mandatory
	    DESCRIPTION
		     "The date and time the event occurred (yyyy/MM/dd HH:mm:ss)" 
     ::= { hpevapaTraps 5 }
     
     hpevapaSeverity OBJECT-TYPE
         SYNTAX      DisplayString
         ACCESS      read-only
         STATUS      mandatory
         DESCRIPTION 
             "Severity of the Alarm"
    ::= { hpevapaTraps 6 }    
     
     hpevapaArray_ID OBJECT-TYPE
         SYNTAX      OCTET STRING
         ACCESS      read-only
    	 STATUS      mandatory
    	 DESCRIPTION 
         "Array ID"
    ::= { hpevapaTraps 7 }

	 hpevapaArray_Name OBJECT-TYPE
     	SYNTAX      OCTET STRING
     	ACCESS      read-only
    	STATUS      mandatory
    	DESCRIPTION 
        "Array Name"
    ::= { hpevapaTraps 8 }

	hpevapaObject_ID OBJECT-TYPE
    	SYNTAX      OCTET STRING
    	ACCESS      read-only
    	STATUS      mandatory
    	DESCRIPTION 
        "Object ID"
    ::= { hpevapaTraps 9 }
    
	hpevapaObject_Type OBJECT-TYPE
    	SYNTAX      OCTET STRING
    	ACCESS      read-only
    	STATUS      mandatory
    	DESCRIPTION 
        "Object Type"
    ::= { hpevapaTraps 10 }

	hpevapaObject_Name OBJECT-TYPE
    	SYNTAX      OCTET STRING
   	 	ACCESS      read-only
    	STATUS      mandatory
   		DESCRIPTION 
        "Object Name"
    ::= { hpevapaTraps 11 }

	hpevapaCounter_Name OBJECT-TYPE
    	SYNTAX      OCTET STRING
    	ACCESS      read-only
   	 	STATUS      mandatory
    	DESCRIPTION 
        "Counter Name of the occured event"
    ::= { hpevapaTraps 12 }  
   
	hpevapaDetect_Level OBJECT-TYPE
   	 	SYNTAX      OCTET STRING
    	ACCESS      read-only
    	STATUS      mandatory
    	DESCRIPTION 
        "Detect level"
    ::= { hpevapaTraps 13 }
 
	hpevapaActual_Value OBJECT-TYPE
    	SYNTAX      OCTET STRING
    	ACCESS      read-only
    	STATUS      mandatory
    	DESCRIPTION 
        "Actual Value"
    ::= { hpevapaTraps 14 }
    
 	hpevapaThreshold_Value OBJECT-TYPE 
    	SYNTAX      OCTET STRING
    	ACCESS      read-only
    	STATUS      mandatory
    	DESCRIPTION 
        "Threshold Value that is being set"
    ::= { hpevapaTraps 15 }
    
 	hpevapaDescription OBJECT-TYPE 
        SYNTAX      OCTET STRING
        ACCESS      read-only
        STATUS      mandatory
        DESCRIPTION 
            "Description"
    ::= { hpevapaTraps 16 }

    
	hpevapaAlarmsTrap TRAP-TYPE
		ENTERPRISE	hpevapaTraps
		VARIABLES {
				hpevapaServer,
				hpevapaSequence_Number,
				hpevapaEvent_Code,
                hpevapaCategory,
                hpevapaTime_Detect,
                hpevapaSeverity,
                hpevapaArray_ID,
                hpevapaArray_Name,
                hpevapaObject_ID,
                hpevapaObject_Type,
                hpevapaObject_Name,
                hpevapaCounter_Name,
                hpevapaDetect_Level,
                hpevapaActual_Value,
                hpevapaThreshold_Value,
                hpevapaDescription}
	DESCRIPTION
		"This is an EVA Performance Advisor Alarms Trap."
	::= 4


 END
